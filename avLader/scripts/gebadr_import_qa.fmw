FME workspace gebadr_import_qa.fmw

Parameters:
- QA_EXCEL =
- LOGFILE =
- NORM_DATABASE =   # Norm-Database
- NORM_PASSWORD =   # Norm-Passwort
- NORM_USERNAME =   # Norm-Username
- VEK1_DATABASE =   # Vek1-Database
- VEK1_PASSWORD =   # Vek1-Passwort
- VEK1_USERNAME =   # Vek1-Username
- Datum:   # Python Script
      from datetime import datetime
      date_game = FME_MacroValues.get('DATE_GAME', None)
      if date_game:
          return date_game
      else:
          return datetime.now().strftime('%Y%m%d')

Writers:
- XLSXW_1: XLSXW to $(QA_EXCEL)

Bookmark: GADRF - Flächen
Note: VEK1P
SQLCreator
    DATASET = $(VEK1_DATABASE)
    EXPOSED_ATTRIBUTE_LIST = BFSNR,PLZ,PLZ_ZUSZIF,ANZAHL
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select t.bfsnr, t.plz, t.plz_zuszif, count(*) anzahl from geodb.gebadr_gadrf t group by t.bfsnr, t.plz, t.plz_zuszif order by t.bfsnr asc, t.plz asc, t.plz_zuszif asc
    RESULT -> StringConcatenator
StringConcatenator
    ACTION = Create New Attribute
    PARM_LINE = @Value(BFSNR)@Value(PLZ)@Value(PLZ_ZUSZIF)
    VAL_ATTR = TEMPKEY
    -> BulkAttributeRenamer_7
BulkAttributeRenamer_7
    ATTRCHOICE = All Attributes
    MODE_CHOICE = RENAME
    PATTERN_ACTION_DISP = ADDSUFFIX
    REPLACE_STR = _ALT
    -> FeatureMerger [REQUESTOR]
Note: TEAMP
SQLCreator_2
    DATASET = $(NORM_DATABASE)
    EXPOSED_ATTRIBUTE_LIST = BFSNR,PLZ,PLZ_ZUSZIF,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select t.bfsnr, t.plz, t.plz_zuszif, count(*) anzahl from gebadr_gadrf t group by t.bfsnr, t.plz, t.plz_zuszif order by t.bfsnr asc, t.plz asc, t.plz_zuszif asc
    RESULT -> StringConcatenator_2
StringConcatenator_2
    ACTION = Create New Attribute
    PARM_LINE = @Value(BFSNR)@Value(PLZ)@Value(PLZ_ZUSZIF)
    VAL_ATTR = TEMPKEY
    -> BulkAttributeRenamer_10
BulkAttributeRenamer_10
    ATTRCHOICE = All Attributes
    MODE_CHOICE = RENAME
    PATTERN_ACTION_DISP = ADDSUFFIX
    REPLACE_STR = _NEU
    -> FeatureMerger [SUPPLIER]
FeatureMerger
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator
    UNMERGED_REQUESTOR -> BulkAttributeRenamer_4
    UNUSED_SUPPLIER -> BulkAttributeRenamer_3
ExpressionEvaluator
    ACTION = Create New Attribute
    EXPRESSION = (@Value(ANZAHL_NEU)-@Value(ANZAHL_ALT))
    VAL_ATTR = DIFF_ABS
    -> ExpressionEvaluator_2
ExpressionEvaluator_2
    ACTION = Create New Attribute
    EXPRESSION = (@Value(DIFF_ABS)/(@Value(ANZAHL_ALT)/100.0))
    VAL_ATTR = DIFF_REL
    -> Sorter
Sorter
    SORT_PARM = DIFF_ABS NUMERIC ASCENDING
    SORTED -> BulkAttributeRenamer_5
BulkAttributeRenamer_5
    ATTRCHOICE = Selected Attributes
    ATTRLIST = BFSNR_ALT PLZ_ALT PLZ_ZUSZIF_ALT
    CASE_DISP = YES
    MODE_CHOICE = RENAME
    PATTERN_ACTION_DISP = REMOVESUFFIX
    REPLACE_STR = _ALT
    -> unveraendertFlächen (writer XLSXW_1)
unveraendertFlächen (writer XLSXW_1)
    attributes: BFSNR number(20), PLZ number(20), PLZ_ZUSZIF number(20), ANZAHL_ALT number(20), ANZAHL_NEU number(20), DIFF_ABS number(20), DIFF_REL number(20)
BulkAttributeRenamer_4
    ATTRCHOICE = All Attributes
    CASE_DISP = YES
    MODE_CHOICE = RENAME
    PATTERN_ACTION_DISP = REMOVESUFFIX
    REPLACE_STR = _ALT
    -> verschwundenFlächen (writer XLSXW_1)
verschwundenFlächen (writer XLSXW_1)
    attributes: BFSNR number(20), PLZ number(20), PLZ_ZUSZIF number(20), ANZAHL number(20)
BulkAttributeRenamer_3
    ATTRCHOICE = All Attributes
    CASE_DISP = YES
    MODE_CHOICE = RENAME
    PATTERN_ACTION_DISP = REMOVESUFFIX
    REPLACE_STR = _NEU
    -> hinzugekommenFlächen (writer XLSXW_1)
hinzugekommenFlächen (writer XLSXW_1)
    attributes: BFSNR number(20), PLZ number(20), PLZ_ZUSZIF number(20), ANZAHL number(20)

Bookmark: GADR - Punkte
Note: VEK1P
SQLCreator_9
    DATASET = $(VEK1_DATABASE)
    EXPOSED_ATTRIBUTE_LIST = BFSNR,PLZ,PLZ_ZUSZIF,ANZAHL
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select t.bfsnr, t.plz, t.plz_zuszif, count(*) anzahl from geodb.gebadr_gadr t group by t.bfsnr, t.plz, t.plz_zuszif order by t.bfsnr asc, t.plz asc, t.plz_zuszif asc
    RESULT -> StringConcatenator_4
StringConcatenator_4
    ACTION = Create New Attribute
    PARM_LINE = @Value(BFSNR)@Value(PLZ)@Value(PLZ_ZUSZIF)
    VAL_ATTR = TEMPKEY
    -> BulkAttributeRenamer_8
BulkAttributeRenamer_8
    ATTRCHOICE = All Attributes
    MODE_CHOICE = RENAME
    PATTERN_ACTION_DISP = ADDSUFFIX
    REPLACE_STR = _ALT
    -> FeatureMerger_2 [REQUESTOR]
Note: TEAMP
SQLCreator_10
    DATASET = $(NORM_DATABASE)
    EXPOSED_ATTRIBUTE_LIST = BFSNR,PLZ,PLZ_ZUSZIF,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select t.bfsnr, t.plz, t.plz_zuszif, count(*) anzahl from gebadr_gadr t group by t.bfsnr, t.plz, t.plz_zuszif order by t.bfsnr asc, t.plz asc, t.plz_zuszif asc
    RESULT -> StringConcatenator_3
StringConcatenator_3
    ACTION = Create New Attribute
    PARM_LINE = @Value(BFSNR)@Value(PLZ)@Value(PLZ_ZUSZIF)
    VAL_ATTR = TEMPKEY
    -> BulkAttributeRenamer_9
BulkAttributeRenamer_9
    ATTRCHOICE = All Attributes
    MODE_CHOICE = RENAME
    PATTERN_ACTION_DISP = ADDSUFFIX
    REPLACE_STR = _NEU
    -> FeatureMerger_2 [SUPPLIER]
FeatureMerger_2
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_3
    UNMERGED_REQUESTOR -> BulkAttributeRenamer_2
    UNUSED_SUPPLIER -> BulkAttributeRenamer
ExpressionEvaluator_3
    ACTION = Create New Attribute
    EXPRESSION = (@Value(ANZAHL_NEU)-@Value(ANZAHL_ALT))
    VAL_ATTR = DIFF_ABS
    -> ExpressionEvaluator_4
ExpressionEvaluator_4
    ACTION = Create New Attribute
    EXPRESSION = (@Value(DIFF_ABS)/(@Value(ANZAHL_ALT)/100.0))
    VAL_ATTR = DIFF_REL
    -> Sorter_2
Sorter_2
    SORT_PARM = DIFF_ABS NUMERIC ASCENDING
    SORTED -> BulkAttributeRenamer_6
BulkAttributeRenamer_6
    ATTRCHOICE = Selected Attributes
    ATTRLIST = BFSNR_ALT PLZ_ALT PLZ_ZUSZIF_ALT
    CASE_DISP = YES
    MODE_CHOICE = RENAME
    PATTERN_ACTION_DISP = REMOVESUFFIX
    REPLACE_STR = _ALT
    -> unveraendertPoint (writer XLSXW_1)
unveraendertPoint (writer XLSXW_1)
    attributes: BFSNR number(20), PLZ number(20), PLZ_ZUSZIF number(20), ANZAHL_ALT number(20), ANZAHL_NEU number(20), DIFF_ABS number(20), DIFF_REL number(30)
BulkAttributeRenamer_2
    ATTRCHOICE = All Attributes
    CASE_DISP = YES
    MODE_CHOICE = RENAME
    PATTERN_ACTION_DISP = REMOVESUFFIX
    REPLACE_STR = _ALT
    -> verschwundenPoint (writer XLSXW_1)
verschwundenPoint (writer XLSXW_1)
    attributes: BFSNR number(20), PLZ number(20), PLZ_ZUSZIF number(20), ANZAHL number(20)
BulkAttributeRenamer
    ATTRCHOICE = All Attributes
    CASE_DISP = YES
    MODE_CHOICE = RENAME
    PATTERN_ACTION_DISP = REMOVESUFFIX
    REPLACE_STR = _NEU
    -> hinzugekommenPoint (writer XLSXW_1)
hinzugekommenPoint (writer XLSXW_1)
    attributes: BFSNR number(20), PLZ number(20), PLZ_ZUSZIF number(20), ANZAHL number(20)

Bookmark: New Bookmark
SQLCreator_4
    DATASET = $(NORM_DATABASE)
    EXPOSED_ATTRIBUTE_LIST = BFSNR,PLZ,ORT,LOKALISAT,GEBNR,ANZAHL,PLZ_ZUSZIF,BE_EDID
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.bfsnr, t.plz, t.ort, t.lokalisat, t.gebnr, t.plz_zuszif, t.be_edid, count(*) anzahl
        from gebadr_gadrf t
        where t.gueltigkt = 1
       group by t.bfsnr, t.plz, t.plz_zuszif, t.ort, t.lokalisat, t.gebnr, t.be_edid
       having count(*) > 1 and gebnr not like '%nn%'
       order by t.bfsnr asc, t.plz asc, t.ort asc, t.lokalisat asc, t.gebnr asc
    RESULT -> doppelte_Flächen (writer XLSXW_1)
doppelte_Flächen (writer XLSXW_1)
    attributes: BFSNR number(20), PLZ number(20), ORT string(20), LOKALISAT string(50), GEBNR string(20), ANZAHL number(20)
SQLCreator_11 [off]
    DATASET = $(NORM_DATABASE)
    EXPOSED_ATTRIBUTE_LIST = BE_GID,GEBNR,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.be_gid, t.gebnr, count(*) anzahl
        from gebadr_gadrf t
       group by t.be_gid, t.gebnr
       having count(*) > 1
       order by t.be_gid asc, t.gebnr asc
    RESULT -> Tester_2
Tester_2 [off]
    BOOL_OP = OR
    TEST_CLAUSE = CASE_INSENSITIVE_TEST @Value(GEBNR) NOT_LIKE nn
    PASSED -> doppelte_Flächen_BE_GID (writer XLSXW_1)
doppelte_Flächen_BE_GID (writer XLSXW_1) [off]
    attributes: BE_GID number(20), GEBNR string(20), ANZAHL number(20)
SQLCreator_6
    COORDSYS = $(NORM_DATABASE)
    DATASET = teamp
    EXPOSED_ATTRIBUTE_LIST = BFSNR,PLZ,LOKALISAT,GEBNR,ANZAHL,PLZ_ZUSZIF,BE_EDID
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.bfsnr, t.plz, t.lokalisat, t.gebnr, t.plz_zuszif, t.be_edid, count(*) anzahl
        from gebadr_gadr t
        where t.gueltigkt = 1
       group by t.bfsnr, t.plz, t.plz_zuszif, t.lokalisat, t.gebnr, t.be_edid
       having count(*) > 1 and gebnr not like '%nn%'
       order by t.bfsnr asc, t.plz asc, t.lokalisat asc, t.gebnr asc
    RESULT -> doppelte_Punkte (writer XLSXW_1)
doppelte_Punkte (writer XLSXW_1)
    attributes: BFSNR number(20), PLZ number(20), LOKALISAT string(50), GEBNR string(20), ANZAHL number(20)
SQLCreator_3 [off]
    DATASET = $(NORM_DATABASE)
    EXPOSED_ATTRIBUTE_LIST = BE_GID,GEBNR,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.be_gid, t.gebnr, count(*) anzahl
        from gebadr_gadr t
       group by t.be_gid, t.gebnr
       having count(*) > 1
       order by t.be_gid asc, t.gebnr asc
    RESULT -> Tester_4
Tester_4 [off]
    BOOL_OP = OR
    TEST_CLAUSE = CASE_INSENSITIVE_TEST @Value(GEBNR) NOT_LIKE nn
    PASSED -> doppelte_Punkte_BE_GID (writer XLSXW_1)
doppelte_Punkte_BE_GID (writer XLSXW_1) [off]
    attributes: BE_GID number(20), GEBNR string(20), ANZAHL number(20)
