FME workspace lk_import_1.fmw

Parameters:
- SourceDataset_XLSXR_5 = J:\z_datauf\GIS_Prod\LKMETA\work\tabelle\LKMETA_WERTETABELLEN.xlsx   # Source Microsoft Excel File(s)
- SourceDataset_XLSXR_4 = T:\NOT_DMS\Projekte\LKBE\DOCP-#637618-v3-LKBE_Etappierung_Gemeinden.XLSX   # Source Microsoft Excel File(s)
- LKBE_gpkg = \\geodb.infra.be.ch\arbeit\Rampe\LKMAP\gpkg\LKMap_be.gpkg   # Geopackage LKBE
- DestDataset_GEODATABASE_FILE = \\bve.be.ch\root\VMA_DATA\NOT_DMS\Projekte\LKBE\Projektfortschritt\LKBE_Projektstand.gdb   # File Geodatabase
- DestDataset_XLSXW = \\bve.be.ch\root\VMA_DATA\NOT_DMS\Projekte\LKBE\Projektfortschritt\LKBE_Lieferungen.xlsx   # Destination Microsoft Excel File
- SourceDataset_XLSXR = T:\NOT_DMS\Projekte\LKBE\Projektfortschritt\LKBE_Lieferungen.xlsx   # Source Microsoft Excel File(s)
- LOGFILE = \\geodb-bkt.infra.be.ch\Freigabe\Anwendungen\avLader\log\lk_import\test.log
- NORM_CONNECTIONFILE = \\geodb.infra.be.ch\arbeit\Anwend\connections\PROD\norm@team.sde   # Connection File
- POSTGIS_DB = team   # Database
- POSTGIS_HOST = a4pa-dl-oereb01.infra.be.ch   # Host
- POSTGIS_PASSWORD =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   # Password
- POSTGIS_PORT = 12890   # Port
- POSTGIS_USER = norm   # Username
- VEK1_CONNECTIONFILE = P:\Z_Systems\GeoDB\Zusatzdaten\geo@vek1p_dc.sde   # Connection File

Readers:
- GEODATABASE_SDE_1: GEODATABASE_SDE
- XLSXR_1: XLSXR from $(SourceDataset_XLSXR_5)
- XLSXR_2: XLSXR from $(SourceDataset_XLSXR_4)
- XLSXR_3: XLSXR from $(SourceDataset_XLSXR)
- GEODATABASE_SDE_2: GEODATABASE_SDE

Writers:
- POSTGIS_1: POSTGIS to $(POSTGIS_DB)
- GEODATABASE_SDE_3: GEODATABASE_SDE
- GEODATABASE_FILE_1: GEODATABASE_FILE to $(DestDataset_GEODATABASE_FILE)
- XLSXW_1: XLSXW to $(DestDataset_XLSXW)

FeatureJoiner_2
    ATTR_CONFLICT_RES = Use Left
    GEOMETRY_HANDLING = Use Left
    JOIN_KEYS = WERK_ID WERK_ID AUTO
    JOIN_MODE = Inner
    JOINED -> FeatureJoiner [LEFT]
Note: get fme datetime
DateTimeConverter
    DATETIME_ATTR = DELIVERY_DATE
    IN_FORMAT = %Y-%m-%d %H:%M:%S$
    OUT_FORMAT = FME
    REPAIR_INPUT = NO
    TEST_INPUT = 2019-12-03 12:18:52
    -> Sorter
Sorter
    SORT_PARM = DELIVERY_UNIT ALPHA ASCENDING DELIVERY_DATE NUMERIC DESCENDING
    SORTED -> DuplicateFilter_2
Note: get latest delivery
DuplicateFilter_2
    INPUT_ORDERED_CHOICE = No
    KEYATTR = DELIVERY_UNIT
    UNIQUE -> DateTimeConverter_2
Note: get fme date
DateTimeConverter_2
    DATETIME_ATTR = DELIVERY_DATE
    IN_FORMAT = FME
    OUT_FORMAT = %Y%m%d
    REPAIR_INPUT = NO
    -> FeatureJoiner [RIGHT]
Aggregator_7
    ACCUM_ATTRS_NAME = Use Attributes From One Feature
    AGGREGATE_TYPE = Homogeneous Collection (If Possible)
    GROUP_BY = DELIVERY_UNIT
    MODE = Geometry - Assemble One Level
    ORDERED = No
    SEP = ,
    SUM = LIEFERUNG
AttributeManager_15
    ATTR_TABLE:
      SET_TO AW = FME_CONDITIONAL:DEFAULT_VALUE'_FME_NO_OP_'BOOL_OP;OR;COMPOSITE_TEST;<Unused>;TEST @Value(MEDIUM_ID) = 1'1'FME_NUM_CONDITIONS2___
      SET_TO WA = FME_CONDITIONAL:DEFAULT_VALUE'_FME_NO_OP_'BOOL_OP;OR;COMPOSITE_TEST;<Unused>;TEST @Value(MEDIUM_ID) = 2'1'FME_NUM_CONDITIONS2___
      SET_TO E = FME_CONDITIONAL:DEFAULT_VALUE'_FME_NO_OP_'BOOL_OP;OR;COMPOSITE_TEST;<Unused>;TEST @Value(MEDIUM_ID) = 3'1'FME_NUM_CONDITIONS2___
      SET_TO GAS = FME_CONDITIONAL:DEFAULT_VALUE'_FME_NO_OP_'BOOL_OP;OR;COMPOSITE_TEST;<Unused>;TEST @Value(MEDIUM_ID) = 4'1'FME_NUM_CONDITIONS2___
      SET_TO KOM = FME_CONDITIONAL:DEFAULT_VALUE'_FME_NO_OP_'BOOL_OP;OR;COMPOSITE_TEST;<Unused>;TEST @Value(MEDIUM_ID) = 5'1'FME_NUM_CONDITIONS2___
      SET_TO FW = FME_CONDITIONAL:DEFAULT_VALUE'_FME_NO_OP_'BOOL_OP;OR;COMPOSITE_TEST;<Unused>;TEST @Value(MEDIUM_ID) = 6'1'FME_NUM_CONDITIONS2___
      SET_TO WM = FME_CONDITIONAL:DEFAULT_VALUE'_FME_NO_OP_'BOOL_OP;OR;COMPOSITE_TEST;<Unused>;TEST @Value(MEDIUM_ID) = 7'1'FME_NUM_CONDITIONS2___
      SET_TO WERKSTAND = 1
    -> AttributeManager_19
AttributeManager_19
    ATTR_TABLE:
      SET_TO LAW = FME_CONDITIONAL:DEFAULT_VALUE'_FME_NO_OP_'BOOL_OP;AND;COMPOSITE_TEST;<Unused>;TEST @Value(AW) = 1;TEST @Value(LIEFERUNG) = 1;TEST @Value(FORMAT_ID) = 1'1'BOOL_OP;AND;COMPOSITE_TEST;<Unused>;TEST @Value(AW) = 1;TEST @Value(LIEFERUNG) = 1;TEST @Value(FORMAT_ID) != 1'2'BOOL_OP;AND;COMPOSITE_TEST;<Unused>;TEST @Value(AW) = 1;TEST @Value(LIEFERUNG) IN 2'3'FME_NUM_CONDITIONS4___
      SET_TO LWA = FME_CONDITIONAL:DEFAULT_VALUE'_FME_NO_OP_'BOOL_OP;AND;COMPOSITE_TEST;<Unused>;TEST @Value(WA) = 1;TEST @Value(LIEFERUNG) = 1;TEST @Value(FORMAT_ID) = 1'1'BOOL_OP;AND;COMPOSITE_TEST;<Unused>;TEST @Value(WA) = 1;TEST @Value(LIEFERUNG) = 1;TEST @Value(FORMAT_ID) != 1'2'BOOL_OP;AND;COMPOSITE_TEST;<Unused>;TEST @Value(WA) = 1;TEST @Value(LIEFERUNG) = 2'3'FME_NUM_CONDITIONS4___
      SET_TO LE = FME_CONDITIONAL:DEFAULT_VALUE'_FME_NO_OP_'BOOL_OP;AND;COMPOSITE_TEST;<Unused>;TEST @Value(E) = 1;TEST @Value(LIEFERUNG) = 1;TEST @Value(FORMAT_ID) = 1'1'BOOL_OP;AND;COMPOSITE_TEST;<Unused>;TEST @Value(E) = 1;TEST @Value(LIEFERUNG) = 1;TEST @Value(FORMAT_ID) != 1'2'BOOL_OP;AND;COMPOSITE_TEST;<Unused>;TEST @Value(E) = 1;TEST @Value(LIEFERUNG) = 2'3'FME_NUM_CONDITIONS4___
      SET_TO LGAS = FME_CONDITIONAL:DEFAULT_VALUE'_FME_NO_OP_'BOOL_OP;AND;COMPOSITE_TEST;<Unused>;TEST @Value(GAS) = 1;TEST @Value(LIEFERUNG) = 1;TEST @Value(FORMAT_ID) = 1'1'BOOL_OP;AND;COMPOSITE_TEST;<Unused>;TEST @Value(GAS) = 1;TEST @Value(LIEFERUNG) = 1;TEST @Value(FORMAT_ID) != 1'2'BOOL_OP;AND;COMPOSITE_TEST;<Unused>;TEST @Value(GAS) = 1;TEST @Value(LIEFERUNG) = 2'3'FME_NUM_CONDITIONS4___
      SET_TO LKOM = FME_CONDITIONAL:DEFAULT_VALUE'_FME_NO_OP_'BOOL_OP;AND;COMPOSITE_TEST;<Unused>;TEST @Value(KOM) = 1;TEST @Value(LIEFERUNG) = 1;TEST @Value(FORMAT_ID) = 1'1'BOOL_OP;AND;COMPOSITE_TEST;<Unused>;TEST @Value(KOM) = 1;TEST @Value(LIEFERUNG) = 1;TEST @Value(FORMAT_ID) != 1'2'BOOL_OP;AND;COMPOSITE_TEST;<Unused>;TEST @Value(KOM) = 1;TEST @Value(LIEFERUNG) = 2'3'FME_NUM_CONDITIONS4___
      SET_TO LFW = FME_CONDITIONAL:DEFAULT_VALUE'_FME_NO_OP_'BOOL_OP;AND;COMPOSITE_TEST;<Unused>;TEST @Value(FW) = 1;TEST @Value(LIEFERUNG) = 1;TEST @Value(FORMAT_ID) = 1'1'BOOL_OP;AND;COMPOSITE_TEST;<Unused>;TEST @Value(FW) = 1;TEST @Value(LIEFERUNG) = 1;TEST @Value(FORMAT_ID) != 1'2'BOOL_OP;AND;COMPOSITE_TEST;<Unused>;TEST @Value(FW) = 1;TEST @Value(LIEFERUNG) = 2'3'FME_NUM_CONDITIONS4___
      SET_TO LWM = FME_CONDITIONAL:DEFAULT_VALUE'_FME_NO_OP_'BOOL_OP;AND;COMPOSITE_TEST;<Unused>;TEST @Value(WM) = 1;TEST @Value(LIEFERUNG) = 1;TEST @Value(FORMAT_ID) = 1'1'BOOL_OP;AND;COMPOSITE_TEST;<Unused>;TEST @Value(WM) = 1;TEST @Value(LIEFERUNG) = 1;TEST @Value(FORMAT_ID) != 1'2'BOOL_OP;AND;COMPOSITE_TEST;<Unused>;TEST @Value(WM) = 1;TEST @Value(LIEFERUNG) = 2'3'FME_NUM_CONDITIONS4___
      SET_TO join_id = @Value(GEM_ID)_@Value(MEDIUM_ID)
    -> BKW_Gemeinde
    -> FeatureJoiner_4 [RIGHT]
BKW_Gemeinde: Inspector
Tester_6
    BOOL_OP = OR
    TEST_CLAUSE = TEST @Value(MEDIUM) ATTRIBUTE_HAS_VALUE ""
    PASSED -> LKMETA_MEDIUMT (writer GEODATABASE_SDE_3)
Tester_2
    BOOL_OP = OR
    TEST_CLAUSE = TEST @Value(ABGABEFORMAT) ATTRIBUTE_HAS_VALUE ""
    PASSED -> AttributeManager_17
AttributeManager_17
    ATTR_TABLE = RENAME_SET_VALUE ABGABEFORMAT > ANGFORMAT
    -> LKMETA_FORMATT (writer GEODATABASE_SDE_3)
Tester_3
    BOOL_OP = OR
    TEST_CLAUSE = TEST @Value(WERKSTAND) ATTRIBUTE_HAS_VALUE ""
    PASSED -> LKMETA_WERKSTAT (writer GEODATABASE_SDE_3)
Tester_4
    BOOL_OP = OR
    TEST_CLAUSE = TEST @Value(DATASTA) ATTRIBUTE_HAS_VALUE ""
    PASSED -> LKMETA_DATASTAT (writer GEODATABASE_SDE_3)
Tester_5
    BOOL_OP = OR
    TEST_CLAUSE = TEST @Value(LIEFERUNG) ATTRIBUTE_HAS_VALUE ""
    PASSED -> LKMETA_LIEFERT (writer GEODATABASE_SDE_3)
Tester_7
    BOOL_OP = AND
    TEST_CLAUSE:
      TEST @Value(SEE) = 0
      TEST @Value(KT) = 2
    PASSED -> AttributeManager_2
AttributeManager_2
    ATTR_TABLE:
      REMOVE OBJECTID
      REMOVE KT
      REMOVE V_KREISNR
      RENAME_SET_VALUE NAME > GEMNAME
      REMOVE SEE
      REMOVE SHAPE.AREA
      REMOVE SHAPE.LEN
      SET_TO MEDIUM_ID
      SET_TO GEMWERK_FREIGABE = 0
    -> Aggregator
Aggregator
    ACCUM_ATTRS_NAME = Get Attributes From One Representative Feature
    AGGREGATE_TYPE = Homogeneous Collection (If Possible)
    GROUP_BY = GMDE
    MODE = Geometry - Assemble One Level
    ORDERED = No
    SEP = ,
    AGGREGATE -> FeatureMerger_9 [REQUESTOR]
    AGGREGATE -> FeatureMerger_10 [REQUESTOR]
    AGGREGATE -> AttributeManager_9
    AGGREGATE -> AttributeManager_7
    AGGREGATE -> AttributeManager_10
    AGGREGATE -> AttributeManager_5
    AGGREGATE -> AttributeManager_8
    AGGREGATE -> AttributeManager_6
    AGGREGATE -> AttributeManager_11
    AGGREGATE -> FeatureJoiner_6 [LEFT]
    AGGREGATE -> FeatureMerger_11 [SUPPLIER]
Note: attribute from right
FeatureJoiner_3
    ATTR_CONFLICT_RES = Use Right
    GEOMETRY_HANDLING = Use Left
    JOIN_KEYS = GMDE BFSNR AUTO
    JOIN_MODE = Inner
    JOINED -> AttributeManager_30
AttributeManager_30
    ATTR_TABLE = SET_TO join_id = @Value(GEM_ID)_@Value(MEDIUM_ID)
    -> FeatureJoiner_4 [LEFT]
FeatureJoiner_4
    ATTR_CONFLICT_RES = Use Right
    GEOMETRY_HANDLING = Use Left
    JOIN_KEYS = join_id join_id AUTO
    JOIN_MODE = Inner
    JOINED -> Aggregator_2
    JOINED -> FeatureMerger_7 [REQUESTOR]
    UNJOINED_LEFT -> AttributeManager_14
AttributeManager_14
    ATTR_TABLE:
      SET_TO LIEFERUNG = 0
      SET_TO WERKSTAND
      SET_TO FORMAT_ID = 0
    -> Aggregator_2
    -> FeatureMerger_7 [REQUESTOR]
AttributeManager_34
    ATTR_TABLE:
      SET_TO LAW = FME_CONDITIONAL:DEFAULT_VALUE'FME_NULL_VALUE'BOOL_OP;OR;COMPOSITE_TEST;<Unused>;TEST LAW ATTRIBUTE_HAS_A_VALUE _FME_BLANK_STRING_'@Value(LAW)'FME_NUM_CONDITIONS2___
      SET_TO LWA = FME_CONDITIONAL:DEFAULT_VALUE'FME_NULL_VALUE'BOOL_OP;OR;COMPOSITE_TEST;<Unused>;TEST LWA ATTRIBUTE_HAS_A_VALUE _FME_BLANK_STRING_'@Value(LWA)'FME_NUM_CONDITIONS2___
      SET_TO LE = FME_CONDITIONAL:DEFAULT_VALUE'FME_NULL_VALUE'BOOL_OP;OR;COMPOSITE_TEST;<Unused>;TEST LE ATTRIBUTE_HAS_A_VALUE _FME_BLANK_STRING_'@Value(LE)'FME_NUM_CONDITIONS2___
      SET_TO LGAS = FME_CONDITIONAL:DEFAULT_VALUE'FME_NULL_VALUE'BOOL_OP;OR;COMPOSITE_TEST;<Unused>;TEST LGAS ATTRIBUTE_HAS_A_VALUE _FME_BLANK_STRING_'@Value(LGAS)'FME_NUM_CONDITIONS2___
      SET_TO LKOM = FME_CONDITIONAL:DEFAULT_VALUE'FME_NULL_VALUE'BOOL_OP;OR;COMPOSITE_TEST;<Unused>;TEST LKOM ATTRIBUTE_HAS_A_VALUE _FME_BLANK_STRING_'@Value(LKOM)'FME_NUM_CONDITIONS2___
      SET_TO LFW = FME_CONDITIONAL:DEFAULT_VALUE'FME_NULL_VALUE'BOOL_OP;OR;COMPOSITE_TEST;<Unused>;TEST LFW ATTRIBUTE_HAS_A_VALUE _FME_BLANK_STRING_'@Value(LFW)'FME_NUM_CONDITIONS2___
      SET_TO LWM = FME_CONDITIONAL:DEFAULT_VALUE'FME_NULL_VALUE'BOOL_OP;OR;COMPOSITE_TEST;<Unused>;TEST LWM ATTRIBUTE_HAS_A_VALUE _FME_BLANK_STRING_'@Value(LWM)'FME_NUM_CONDITIONS2___
      SET_TO L_SUM = @Value(LAW);@Value(LE);@Value(LFW);@Value(LGAS);@Value(LKOM);@Value(LWA);@Value(LWM)
    -> StringReplacer
StringReplacer
    CASE = NO
    FIND_TEXT = " "
    NO_MATCH = _FME_NO_OP_
    REGEXP = NO
    SRC_ATTRS = L_SUM
    -> AttributeSplitter
AttributeSplitter
    ATTR_NAME = L_SUM
    DELIMITER = ;
    DROP_EMPTY_PARTS = No
    LIST_NAME = _list
    TRIM_OPTION = Both
    -> ListExploder
ListExploder
    ATTR_ACCUM_MODE = Merge List Attributes
    ATTR_CONFLICT_RES = Use List Attribute Values
    INDEX_ATTR = _element_index
    LIST_ATTR = _list{}
    ELEMENTS -> StatisticsCalculator
StatisticsCalculator
    COMPUTE_HISTOGRAM = NO
    COUNT_ATTR = _count
    GROUP_BY = BFSNR _list
    PREPEND_ATTR_NAME_CHOICE = For multiple results only
    STATS_ATTRS = _list
    SUMMARY -> TestFilter_2
TestFilter_2
    DEFAULT_VALUE = <UNFILTERED>
    TEST_LIST = "BOOL_OP,OR,COMPOSITE_TEST,""""""<Unused>"""""",TEST_CLAUSE,TEST @Value(_list) = 1",geliefert,"BOOL_OP,OR,COMPOSITE_TEST,""""""<Unused>"""""",TEST_CLAUSE,TEST @Value(_list) = 2",nicht geliefert
    geliefert -> AttributeManager_33
    nicht geliefert -> AttributeManager_33
AttributeManager_33
    ATTR_TABLE = REMOVE _list
    -> Aggregator_8
Aggregator_8
    ACCUM_ATTRS_NAME = Use Attributes From One Feature
    AGGREGATE_TYPE = Homogeneous Collection (If Possible)
    GROUP_BY = BFSNR
    MODE = Geometry - Assemble One Level
    ORDERED = No
    SEP = ,
    SUM = _count
    AGGREGATE -> FeatureJoiner_7 [RIGHT]
FeatureJoiner_7
    ATTR_CONFLICT_RES = Use Left
    GEOMETRY_HANDLING = Use Left
    JOIN_KEYS = BFSNR BFSNR AUTO
    JOIN_MODE = Inner
    JOINED -> AttributeManager_35
AttributeManager_35
    ATTR_TABLE:
      REMOVE MEDIUM_ID
      REMOVE WA
      REMOVE KOM
      REMOVE E
      REMOVE AW
      REMOVE GAS
      REMOVE FW
      REMOVE WM
      REMOVE GEM_ID
      REMOVE LAW
      REMOVE LWA
      REMOVE LE
      REMOVE LGAS
      REMOVE LKOM
      REMOVE LFW
      REMOVE LWM
      SET_TO DATASTAND = FME_CONDITIONAL:DEFAULT_VALUE'_FME_NO_OP_'BOOL_OP;OR;COMPOSITE_TEST;<Unused>;TEST @Value(DATASTAND) = 1'@Value(DATASTAND)'BOOL_OP;OR;COMPOSITE_TEST;<Unused>;TEST @Value(DATASTAND) = 2'@Value(DATASTAND)'BOOL_OP;OR;COMPOSITE_TEST;<Unused>;TEST @Value(DATASTAND) = 4'10'BOOL_OP;AND;COMPOSITE_TEST;<Unused>;TEST @Value(DATASTAND) = 3;TEST @Value(_count) = 7'9'BOOL_OP;AND;COMPOSITE_TEST;<Unused>;TEST @Value(DATASTAND) = 3;TEST @Value(_count) = 6'8'BOOL_OP;AND;COMPOSITE_TEST;<Unused>;TEST @Value(DATASTAND) = 3;TEST @Value(_count) = 5'7'BOOL_OP;AND;COMPOSITE_TEST;<Unused>;TEST @Value(DATASTAND) = 3;TEST @Value(_count) = 4'6'BOOL_OP;AND;COMPOSITE_TEST;<Unused>;TEST @Value(DATASTAND) = 3;TEST @Value(_count) = 3'5'BOOL_OP;AND;COMPOSITE_TEST;<Unused>;TEST @Value(DATASTAND) = 3;TEST @Value(_count) = 2'4'BOOL_OP;AND;COMPOSITE_TEST;<Unused>;TEST @Value(DATASTAND) = 3;TEST @Value(_count) = 1'3'FME_NUM_CONDITIONS11___
      REMOVE join_id
      REMOVE CREATE_DATE
      REMOVE DELIVERY_DATE
      RENAME_SET_VALUE _count > MEDIUM_GELIEFERT
    -> LKBE_STAND_DETAIL (writer GEODATABASE_FILE_1)
Note: < 31.12.2022
Tester_9
    BOOL_OP = OR
    TEST_CLAUSE = TEST @Value(DATUM_START) < 20221231
    PASSED -> DateTimeConverter_3
DateTimeConverter_3
    DATETIME_ATTR = DATUM_END DATUM_START
    IN_FORMAT = %Y%m%d$
    OUT_FORMAT = %Y-%m-%d
    REPAIR_INPUT = NO
    -> AttributeManager_32
AttributeManager_32
    ATTR_TABLE:
      SET_TO DATE_START_STRING = '@Value(DATUM_START)'
      SET_TO DATE_END_STRING = '@Value(DATUM_END)'
    -> SQLExecutor [INITIATOR]
    -> SQLExecutor_2 [INITIATOR]
    -> SQLExecutor_3 [INITIATOR]
Note: Count deliveries
SQLExecutor
    COMBINE_ATTRS = Keep Initiator Attributes if Conflict
    COMBINE_GEOM = Initiator Geometry Only
    DATASET = $(LKBE_gpkg)
    EXPOSED_ATTRIBUTE_LIST = COUNT_D
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    SQL_STATEMENT:
      select count(T_Id) as COUNT_D from meta_deliveries
      where date(@Value(DATE_START_STRING)) < updated_at AND updated_at < date(@Value(DATE_END_STRING))
    RESULT -> FeatureMerger_13 [REQUESTOR]
Note: Count Units
SQLExecutor_2
    COMBINE_ATTRS = Keep Initiator Attributes if Conflict
    COMBINE_GEOM = Initiator Geometry Only
    DATASET = $(LKBE_gpkg)
    EXPOSED_ATTRIBUTE_LIST = COUNT_U
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    SQL_STATEMENT:
      select count(T_Id) as COUNT_U from meta_delivery_units
      where date(@Value(DATE_START_STRING)) < created_at AND created_at < date(@Value(DATE_END_STRING))
    RESULT -> FeatureMerger_13 [SUPPLIER]
FeatureMerger_13
    ATTR_ACCUM_MODE = Merge Supplier
    ATTR_CONFLICT_RES = Use Requestor
    IGNORE_NULLS = No
    JOIN_KEYS = @Value(DATUM_START) @Value(DATUM_START) AUTO
    MERGE_TYPE = Attributes Only
    PROCESS_DUPS = NO
    REJECT_NULL_MISSING_KEYS = No
    SUPPLIERS_FIRST = No
    MERGED -> FeatureMerger_12 [REQUESTOR]
Note: Count Units delivered
SQLExecutor_3
    COMBINE_ATTRS = Keep Initiator Attributes if Conflict
    COMBINE_GEOM = Initiator Geometry Only
    DATASET = $(LKBE_gpkg)
    EXPOSED_ATTRIBUTE_LIST = COUNT_UD
    FORMAT = GEOPACKAGE
    GEOPACKAGE_ENCODE_FEATURE_TYPE_AND_ATTR_NAMES = YES
    GEOPACKAGE_ENFORCE_FOREIGN_KEY_INTEGRITY = YES
    GEOPACKAGE_OPEN_SINGLE_RASTER_AS_SUBDATASET = YES
    GEOPACKAGE_QUERY_FEATURE_TYPES_FOR_MERGE_FILTERS = Yes
    GEOPACKAGE_READ_BOOLEANS_AS_YES_NO = YES
    GEOPACKAGE_READ_NULLS = YES
    SQL_STATEMENT:
      select count(distinct mdu.T_Id) as COUNT_UD from meta_delivery_units mdu
      inner join meta_deliveries md on mdu.id = md.delivery_unit_id
      where date(@Value(DATE_START_STRING)) < mdu.created_at AND mdu.created_at < date(@Value(DATE_END_STRING))
    RESULT -> FeatureMerger_12 [SUPPLIER]
FeatureMerger_12
    ATTR_ACCUM_MODE = Merge Supplier
    ATTR_CONFLICT_RES = Use Requestor
    IGNORE_NULLS = No
    JOIN_KEYS = @Value(DATUM_START) @Value(DATUM_START) AUTO
    MERGE_TYPE = Attributes Only
    PROCESS_DUPS = NO
    REJECT_NULL_MISSING_KEYS = No
    SUPPLIERS_FIRST = No
    MERGED -> AttributeManager_31
AttributeManager_31
    ATTR_TABLE:
      RENAME_SET_VALUE DATUM_START > DATE
      REMOVE DATUM_END
      REMOVE DATE_START_STRING
      REMOVE DATE_END_STRING
      RENAME_SET_VALUE COUNT_D > COUNT_DELIVERY
      RENAME_SET_VALUE COUNT_U > COUNT_UNIT
      RENAME_SET_VALUE COUNT_UD > COUNT_UNIT_DELIVERED
    -> DateTimeConverter_4
DateTimeConverter_4
    DATETIME_ATTR = DATE
    IN_FORMAT = %Y-%m-%d$
    OUT_FORMAT = FME
    REPAIR_INPUT = NO
    -> DATA (writer XLSXW_1)
AttributeManager_23
    ATTR_TABLE = SET_TO DVSKONTAKT = FME_CONDITIONAL:DEFAULT_VALUE'http://@Value(DVSKONTAKT)'BOOL_OP;OR;COMPOSITE_TEST;<Unused>;TEST @Value(DVSKONTAKT) BEGINS_WITH http://;TEST @Value(DVSKONTAKT) BEGINS_WITH https://'@Value(DVSKONTAKT)'BOOL_OP;OR;COMPOSITE_TEST;<Unused>;TEST DVSKONTAKT ATTRIBUTE_VALUE_NULL _FME_BLANK_STRING_'-'FME_NUM_CONDITIONS3___
    -> FeatureMerger_3 [SUPPLIER]
    -> FeatureMerger_7 [SUPPLIER]
FeatureMerger_3
    ATTR_ACCUM_MODE = Merge Supplier
    ATTR_CONFLICT_RES = Use Requestor
    IGNORE_NULLS = No
    JOIN_KEYS = @Value(BFSNR) @Value(BFSNR) AUTO
    MERGE_TYPE = Attributes Only
    PROCESS_DUPS = NO
    REJECT_NULL_MISSING_KEYS = No
    SUPPLIERS_FIRST = No
    MERGED -> AttributeManager_4
    UNMERGED_REQUESTOR -> AttributeManager_3
FeatureMerger_7
    ATTR_ACCUM_MODE = Merge Supplier
    ATTR_CONFLICT_RES = Use Requestor
    CONNECT_Z_MODE = First Wins
    GEOM_TYPE = Build Polygons
    IGNORE_NULLS = No
    JOIN_KEYS = @Value(GEM_ID) @Value(GEM_ID) AUTO
    MERGE_TYPE = Attributes Only
    PROCESS_DUPS = Yes
    REJECT_NULL_MISSING_KEYS = No
    SUPPLIERS_FIRST = No
    MERGED -> AttributeManager_18
    NOT_MERGED -> AttributeManager_18
Note: Auswertung mit GEMWERK_FREIGABE
AttributeManager_18
    ATTR_TABLE:
      REMOVE AW
      REMOVE KOM
      REMOVE FW
      REMOVE WM
      REMOVE E
      REMOVE WA
      REMOVE GAS
      REMOVE GEM_ID
      REMOVE INTRO
      RENAME_SET_VALUE DELIVERY_UNIT > LIEFERID
      RENAME_SET_VALUE FORMAT_ID > ANGFORMAT
      SET_TO WERK = FME_CONDITIONAL:DEFAULT_VALUE'@Value(WERK)'BOOL_OP;OR;COMPOSITE_TEST;<Unused>;TEST WERK ATTRIBUTE_IS_MISSING _FME_BLANK_STRING_;TEST WERK ATTRIBUTE_VALUE_NULL _FME_BLANK_STRING_'-'FME_NUM_CONDITIONS2___
      SET_TO WERKK = FME_CONDITIONAL:DEFAULT_VALUE'@Value(WERKK)'BOOL_OP;OR;COMPOSITE_TEST;<Unused>;TEST WERKK ATTRIBUTE_IS_MISSING _FME_BLANK_STRING_;TEST WERKK ATTRIBUTE_VALUE_NULL _FME_BLANK_STRING_'-'FME_NUM_CONDITIONS2___
      SET_TO WERKPHONE = FME_CONDITIONAL:DEFAULT_VALUE'@Value(WERKPHONE)'BOOL_OP;OR;COMPOSITE_TEST;<Unused>;TEST WERKPHONE ATTRIBUTE_IS_MISSING _FME_BLANK_STRING_;TEST WERKPHONE ATTRIBUTE_VALUE_NULL _FME_BLANK_STRING_'-'FME_NUM_CONDITIONS2___
      SET_TO DVSKONTAKT = FME_CONDITIONAL:DEFAULT_VALUE'@Value(DVSKONTAKT)'BOOL_OP;OR;COMPOSITE_TEST;<Unused>;TEST DVSKONTAKT ATTRIBUTE_IS_MISSING _FME_BLANK_STRING_;TEST DVSKONTAKT ATTRIBUTE_VALUE_NULL _FME_BLANK_STRING_'-'FME_NUM_CONDITIONS2___
      SET_TO DVSNAME = FME_CONDITIONAL:DEFAULT_VALUE'@Value(DVSNAME)'BOOL_OP;OR;COMPOSITE_TEST;<Unused>;TEST DVSNAME ATTRIBUTE_VALUE_NULL _FME_BLANK_STRING_;TEST DVSNAME ATTRIBUTE_IS_MISSING _FME_BLANK_STRING_'-'FME_NUM_CONDITIONS2___
      SET_TO WERKSTAND = FME_CONDITIONAL:DEFAULT_VALUE'0'BOOL_OP;OR;COMPOSITE_TEST;<Unused>;TEST @Value(WERKSTAND) = 1'1'BOOL_OP;AND;COMPOSITE_TEST;<Unused>;TEST WERKSTAND ATTRIBUTE_IS_EMPTY _FME_BLANK_STRING_;TEST @Value(GEMWERK_FREIGABE) = 1'2'FME_NUM_CONDITIONS3___
      REMOVE LAW
      REMOVE LWA
      REMOVE LE
      REMOVE LGAS
      REMOVE LKOM
      REMOVE LFW
      REMOVE LWM
      SET_TO WERKORT = FME_CONDITIONAL:DEFAULT_VALUE'@Value(WERKADDRESS), @Value(WERKZIP) @Value(WERKCITY)'BOOL_OP;AND;COMPOSITE_TEST;<Unused>;TEST WERKCITY ATTRIBUTE_IS_MISSING _FME_BLANK_STRING_;TEST WERKADDRESS ATTRIBUTE_IS_MISSING _FME_BLANK_STRING_'-'FME_NUM_CONDITIONS2___
      RENAME_SET_VALUE DELIVERY_DATE > LIEFERDATE
    -> DuplicateFilter
Note: Doppelte Werke je Gemeinde und Medium Filtern. / z.B. durch Gemeindefusionen.
DuplicateFilter
    INPUT_ORDERED_CHOICE = No
    KEYATTR = MEDIUM_ID BFSNR WERK LIEFERID
    UNIQUE -> AttributeValueMapper
    DUPLICATE -> DuplicateFilter_Duplicate
AttributeValueMapper
    DIRECTION = Forward (Source To Destination)
    LUT = 1,AW,2,WA,3,E,4,GAS,5,KOM,6,FW,7,WM
    SRC = MEDIUM_ID
    VAL_ATTR = MEDIUM
    -> LKMETA_WERKMETA (writer GEODATABASE_SDE_3)
    -> AttributeManager_22
AttributeManager_22
    ATTR_TABLE:
      SET_TO GEM_MED = @Value(BFSNR)_@Value(MEDIUM_ID)
      SET_TO GEM_MED_LIEFER = @Value(BFSNR)_@Value(MEDIUM_ID)_@Value(LIEFERUNG)
      SET_TO
    -> Aggregator_4
Aggregator_4
    ACCUM_ATTRS_NAME = Use Attributes From One Feature
    AGGREGATE_TYPE = Homogeneous Collection (If Possible)
    COUNT_ATTR = _count_GEM_MED_LIEFER
    GROUP_BY = GEM_MED_LIEFER
    MODE = Geometry - Assemble One Level
    ORDERED = No
    SEP = ,
    AGGREGATE -> AttributeManager_27
AttributeManager_27
    ATTR_TABLE:
      SET_TO C_SENT = FME_CONDITIONAL:DEFAULT_VALUE'_FME_NO_OP_'BOOL_OP;OR;COMPOSITE_TEST;<Unused>;TEST @Value(LIEFERUNG) = 1'@Value(_count_GEM_MED_LIEFER)'BOOL_OP;OR;COMPOSITE_TEST;<Unused>;TEST @Value(LIEFERUNG) = 0'0'FME_NUM_CONDITIONS3___
      SET_TO C_NOTSENT = FME_CONDITIONAL:DEFAULT_VALUE'_FME_NO_OP_'BOOL_OP;OR;COMPOSITE_TEST;<Unused>;TEST @Value(LIEFERUNG) = 2'@Value(_count_GEM_MED_LIEFER)'BOOL_OP;OR;COMPOSITE_TEST;<Unused>;TEST @Value(LIEFERUNG) = 0'0'FME_NUM_CONDITIONS3___
    -> Aggregator_3
Aggregator_3
    ACCUM_ATTRS_NAME = Use Attributes From One Feature
    AGGREGATE_TYPE = Homogeneous Collection (If Possible)
    GROUP_BY = GEM_MED
    MODE = Geometry - Assemble One Level
    ORDERED = No
    SEP = ,
    SUM = C_NOTSENT C_SENT
    AGGREGATE -> AttributeManager_28
AttributeManager_28
    ATTR_TABLE:
      SET_TO PERC_SENT = FME_CONDITIONAL:DEFAULT_VALUE'@Evaluate(100/(@Value(C_SENT)+@Value(C_NOTSENT))*@Value(C_SENT))'BOOL_OP;AND;COMPOSITE_TEST;<Unused>;TEST @Value(C_NOTSENT) = 0;TEST @Value(C_SENT) = 0'0'FME_NUM_CONDITIONS2___
      SET_TO C_TOTAL = @Evaluate(@Value(C_SENT)+@Value(C_NOTSENT))
    -> AttributeKeeper
    -> Aggregator_5
    -> Aggregator_6
Aggregator_6
    ACCUM_ATTRS_NAME = Use Attributes From One Feature
    AGGREGATE_TYPE = Homogeneous Collection (If Possible)
    GROUP_BY = BFSNR MEDIUM
    MODE = Geometry - Assemble One Level
    ORDERED = No
    SEP = ,
    AGGREGATE -> TestFilter
TestFilter
    DEFAULT_VALUE = unfiltered
    TEST_LIST = "BOOL_OP,OR,COMPOSITE_TEST,""""""<Unused>"""""",TEST_CLAUSE,TEST @Value(MEDIUM) = AW",AW,"BOOL_OP,OR,COMPOSITE_TEST,""""""<Unused>"""""",TEST_CLAUSE,TEST @Value(MEDIUM) = WA",WA,"BOOL_OP,OR,COMPOSITE_TEST,""""""<Unused>"""""",TEST_CLAUSE,TEST @Value(MEDIUM) = GAS",GAS,"BOOL_OP,OR,COMPOSITE_TEST,""""""<Unused>"""""",TEST_CLAUSE,TEST @Value(MEDIUM) = FW",FW,"BOOL_OP,OR,COMPOSITE_TEST,""""""<Unused>"""""",TEST_CLAUSE,TEST @Value(MEDIUM) = E",E,"BOOL_OP,OR,COMPOSITE_TEST,""""""<Unused>"""""",TEST_CLAUSE,TEST @Value(MEDIUM) = KOM",KOM,"BOOL_OP,OR,COMPOSITE_TEST,""""""<Unused>"""""",TEST_CLAUSE,TEST @Value(MEDIUM) = WM",WM
AttributeKeeper
    KEEP_ATTRS = C_SENT,PERC_SENT,C_NOTSENT,GEMNAME,C_TOTAL,MEDIUM,BFSNR,DVSNAME
    -> FeatureMerger_11 [REQUESTOR]
FeatureMerger_11
    ATTR_ACCUM_MODE = Merge Supplier
    ATTR_CONFLICT_RES = Use Supplier
    CLEANING_TOLERANCE = None
    CONNECT_Z_MODE = First Wins
    GEOM_TYPE = Build Polygons
    IGNORE_NULLS = No
    JOIN_KEYS = @Value(BFSNR) @Value(GMDE) AUTO
    MERGE_TYPE = Attributes and Geometry
    PROCESS_DUPS = YES
    REJECT_NULL_MISSING_KEYS = No
    SUPPLIERS_FIRST = No
    MERGED -> LKBE_AUSWERTUNG_LIEFERUNGEN (writer GEODATABASE_FILE_1)
Aggregator_5
    ACCUM_ATTRS_NAME = Use Attributes From One Feature
    AGGREGATE_TYPE = Homogeneous Collection (If Possible)
    GROUP_BY = BFSNR
    MODE = Geometry - Assemble One Level
    ORDERED = No
    SEP = ,
    SUM = C_SENT C_NOTSENT C_TOTAL
    AGGREGATE -> AttributeManager_29
AttributeManager_29
    ATTR_TABLE = SET_TO PERC_SENT = FME_CONDITIONAL:DEFAULT_VALUE'@Evaluate(100/(@Value(C_SENT)+@Value(C_NOTSENT))*@Value(C_SENT))'BOOL_OP;AND;COMPOSITE_TEST;<Unused>;TEST @Value(C_NOTSENT) = 0;TEST @Value(C_SENT) = 0'0'FME_NUM_CONDITIONS2___
    -> AttributeKeeper_2
AttributeKeeper_2
    KEEP_ATTRS = C_SENT,PERC_SENT,C_NOTSENT,GEMNAME,C_TOTAL,BFSNR,DVSNAME
    -> FeatureMerger_10 [SUPPLIER]
FeatureMerger_10
    ATTR_ACCUM_MODE = Merge Supplier
    ATTR_CONFLICT_RES = Use Requestor
    IGNORE_NULLS = No
    JOIN_KEYS = @Value(GMDE) @Value(BFSNR) AUTO
    MERGE_TYPE = Attributes Only
    PROCESS_DUPS = NO
    REJECT_NULL_MISSING_KEYS = No
    SUPPLIERS_FIRST = No
    MERGED -> LKBE_AUSWERTUNG_GEMEINDEN (writer GEODATABASE_FILE_1)
DuplicateFilter_Duplicate: Inspector
AttributeManager
    ATTR_TABLE:
      REMOVE ständige Bev.
      REMOVE Fläche _ha_
      REMOVE geplantes Jahr
      RENAME_SET_VALUE Jahr für LKMETA > JAHRPLAN
      REMOVE Rückmeldung erhalten
      REMOVE Rückmeldung (Freitext)
      REMOVE Jahr ohne Rückmeldung
      REMOVE Einwohner ohne Rückmeldung
      REMOVE Fläche ohne Rückmeldung
      REMOVE Kategorie Statistik Einführung
      REMOVE DVS
      REMOVE Vertrag
      REMOVE Kontakt Gemeinde
      REMOVE R
      REMOVE S
      REMOVE T
      REMOVE U
      REMOVE V
    -> Tester_8
Tester_8
    BOOL_OP = OR
    TEST_CLAUSE = TEST BFSNR ATTRIBUTE_HAS_A_VALUE ""
    PASSED -> FeatureJoiner_5 [RIGHT]
FeatureJoiner_5
    ATTR_CONFLICT_RES = Use Left
    GEOMETRY_HANDLING = Use Left
    JOIN_KEYS = BFSNR BFSNR AUTO
    JOIN_MODE = Inner
    JOINED -> FeatureJoiner_6 [RIGHT]
    UNJOINED_LEFT -> Inspector
Note: Erneuter FMerger nötig, da Aggregator mit identischen Geometrien in ESRI nur leere Donuts bildet.
FeatureJoiner_6
    ATTR_CONFLICT_RES = Use Left
    GEOMETRY_HANDLING = Use Left
    JOIN_KEYS = GMDE BFSNR AUTO
    JOIN_MODE = Inner
    JOINED -> LKMETA_STAND (writer GEODATABASE_SDE_3)
Inspector

Bookmark: Gemeinde-Info
SQLCreator_4
    DATASET = $(LKBE_gpkg)
    EXPOSED_ATTRIBUTE_LIST = BFSNR,GEM_ID,GEMWERK_FREIGABE,INTRO
    FORMAT = SQLITE3
    SQLITE3_QUERY_FEATURE_TYPES_FOR_MERGE_FILTERS = Yes
    SQLITE3_SUPPORT_INTERNATIONALIZATION = YES
    SQL_STATEMENT:
      select m.id as GEM_ID, m.bfs as BFSNR, m.introduced as INTRO, complete as GEMWERK_FREIGABE
      from meta_municipalities as m
    RESULT -> FeatureJoiner_3 [RIGHT]

Bookmark: meta_operator_delivery_municipality
SQLCreator_2
    DATASET = $(LKBE_gpkg)
    EXPOSED_ATTRIBUTE_LIST = CREATE_DATE,DELIVERY_UNIT,FORMAT,FORMAT_ID,GEM_ID,MEDIUM_ID,WERK_ID
    FORMAT = SQLITE3
    SQLITE3_QUERY_FEATURE_TYPES_FOR_MERGE_FILTERS = Yes
    SQLITE3_SUPPORT_INTERNATIONALIZATION = YES
    SQL_STATEMENT:
      select mdu.delivery_format_id as FORMAT_ID, mdu.created_at as CREATE_DATE, mdf.aname as FORMAT, mduc.delivery_unit_id as DELIVERY_UNIT, mduc.medium_id as MEDIUM_ID, mduc.operator_id as WERK_ID, mduc.municipality_id as GEM_ID from meta_companies as c, meta_delivery_units as mdu, meta_delivery_formats as mdf, meta_delivery_unit_configs as mduc, meta_municipalities as m
      WHERE c.Id = mduc.operator_id and mduc.delivery_unit_id = mdu.id and mdf.Id = mdu.delivery_format_id and m.id = mduc.municipality_id
    RESULT -> FeatureJoiner_2 [LEFT]

Bookmark: meta_operators
SQLCreator_3
    DATASET = $(LKBE_gpkg)
    EXPOSED_ATTRIBUTE_LIST = WERK,WERK_ID,WERKADDRESS,WERKCITY,WERKK,WERKPHONE,WERKZIP
    FORMAT = SQLITE3
    SQLITE3_QUERY_FEATURE_TYPES_FOR_MERGE_FILTERS = Yes
    SQLITE3_SUPPORT_INTERNATIONALIZATION = YES
    SQL_STATEMENT:
      select c.id as WERK_ID, c.aname as WERK, c.web as WERKK, c.phone as WERKPHONE, c.address as WERKADDRESS, c.zip as WERKZIP, c.city as WERKCITY  from meta_company_company_role as ccr, meta_companies as c
      WHERE ccr.company_role_id = 2 and ccr.company_id = c.id
    RESULT -> AttributeManager_21

Bookmark: URL anpassen
AttributeManager_21
    ATTR_TABLE = SET_TO WERKK = FME_CONDITIONAL:DEFAULT_VALUE'http://@Value(WERKK)'BOOL_OP;OR;COMPOSITE_TEST;<Unused>;TEST @Value(WERKK) BEGINS_WITH http://;TEST @Value(WERKK) BEGINS_WITH https://'@Value(WERKK)'BOOL_OP;OR;COMPOSITE_TEST;<Unused>;TEST WERKK ATTRIBUTE_VALUE_NULL _FME_BLANK_STRING_;TEST WERKK ATTRIBUTE_IS_MISSING _FME_BLANK_STRING_;TEST WERKK ATTRIBUTE_IS_EMPTY _FME_BLANK_STRING_'-'FME_NUM_CONDITIONS3___
    -> FeatureJoiner_2 [RIGHT]

Bookmark: Lieferdaten
SQLCreator_6
    DATASET = $(LKBE_gpkg)
    EXPOSED_ATTRIBUTE_LIST = DELIVERY_DATE,DELIVERY_UNIT
    FORMAT = SQLITE3
    SQLITE3_QUERY_FEATURE_TYPES_FOR_MERGE_FILTERS = Yes
    SQLITE3_SUPPORT_INTERNATIONALIZATION = YES
    SQL_STATEMENT = select delivery_unit_id as DELIVERY_UNIT, updated_at as DELIVERY_DATE from meta_deliveries
    RESULT -> DateTimeConverter

Bookmark: Lieferung abfüllen
FeatureJoiner
    ATTR_CONFLICT_RES = Use Left
    GEOMETRY_HANDLING = Use Left
    JOIN_KEYS = DELIVERY_UNIT DELIVERY_UNIT AUTO
    JOIN_MODE = Inner
    JOINED -> AttributeManager_12
    UNJOINED_LEFT -> AttributeManager_13
AttributeManager_12
    ATTR_TABLE = SET_TO LIEFERUNG = 1
    -> AttributeManager_15
    -> Aggregator_7
AttributeManager_13
    ATTR_TABLE = SET_TO LIEFERUNG = FME_CONDITIONAL:DEFAULT_VALUE'0'BOOL_OP;OR;COMPOSITE_TEST;<Unused>;TEST @Value(FORMAT_ID) < 4'2'FME_NUM_CONDITIONS2___
    -> AttributeManager_15

Bookmark: Wertetabellen
MEDIUM (reader XLSXR_1)
    attributes: MEDIUM number(2,0), BEZ_DE char(15), BEZ_FR char(21)
    -> Tester_6
ABGABEFORMAT (reader XLSXR_1)
    attributes: ABGABEFORMAT number(2,0), BEZ_DE char(22), BEZ_FR char(25)
    -> Tester_2
WERKSTAND (reader XLSXR_1)
    attributes: WERKSTAND number(2,0), BEZ_DE char(20), BEZ_FR char(18)
    -> Tester_3
DATASTA (reader XLSXR_1)
    attributes: DATASTA number(2,0), BEZ_DE char(30), BEZ_FR char(44)
    -> Tester_4
LIEFERUNG (reader XLSXR_1)
    attributes: LIEFERUNG number(2,0), BEZ_DE char(22), BEZ_FR char(29)
    -> Tester_5

Bookmark: Wetetabellen
LKMETA_MEDIUMT (writer GEODATABASE_SDE_3)
    attributes: MEDIUM char(3), BEZ_DE char(50), BEZ_FR char(50)
LKMETA_FORMATT (writer GEODATABASE_SDE_3)
    attributes: ANGFORMAT smallint, BEZ_DE char(30), BEZ_FR char(30)
LKMETA_WERKSTAT (writer GEODATABASE_SDE_3)
    attributes: WERKSTAND smallint, BEZ_DE char(30), BEZ_FR char(30)
LKMETA_DATASTAT (writer GEODATABASE_SDE_3)
    attributes: DATASTA smallint, BEZ_DE char(50), BEZ_FR char(50)
LKMETA_LIEFERT (writer GEODATABASE_SDE_3)
    attributes: LIEFERUNG smallint, BEZ_DE char(30), BEZ_FR char(30)

Bookmark: Input Geometrien
GRENZ5_G5 (reader GEODATABASE_SDE_2) [off]
    attributes: OBJECTID integer, KT smallint, V_KREISNR smallint, GMDE smallint, NAME char(31), SEE smallint, SHAPE.AREA double, SHAPE.LEN double
    -> Tester_7
GENGRZ5_GENG5 (reader GEODATABASE_SDE_1)
    attributes: OBJECTID integer, KT smallint, V_KREISNR smallint, GMDE smallint, NAME char(31), SEE smallint, SHAPE.AREA double, SHAPE.LEN double
    -> Tester_7

Bookmark: Mind. einen Eintrag pro Medium
AttributeManager_5
    ATTR_TABLE:
      SET_TO AW
      SET_TO MEDIUM_ID = 1
    -> FeatureJoiner_3 [LEFT]
AttributeManager_6
    ATTR_TABLE:
      SET_TO E
      SET_TO MEDIUM_ID = 3
    -> FeatureJoiner_3 [LEFT]
AttributeManager_7
    ATTR_TABLE:
      SET_TO FW
      SET_TO MEDIUM_ID = 6
    -> FeatureJoiner_3 [LEFT]
AttributeManager_8
    ATTR_TABLE:
      SET_TO GAS
      SET_TO MEDIUM_ID = 4
    -> FeatureJoiner_3 [LEFT]
AttributeManager_9
    ATTR_TABLE:
      SET_TO KOM
      SET_TO MEDIUM_ID = 5
    -> FeatureJoiner_3 [LEFT]
AttributeManager_10
    ATTR_TABLE:
      SET_TO WA
      SET_TO MEDIUM_ID = 2
    -> FeatureJoiner_3 [LEFT]
AttributeManager_11
    ATTR_TABLE:
      SET_TO WM
      SET_TO MEDIUM_ID = 7
    -> FeatureJoiner_3 [LEFT]

Bookmark: Werkstand pro Gemeinde und Medium festlegen
Aggregator_2
    ACCUM_ATTRS_NAME = Merge Incoming Attributes
    AGGREGATE_TYPE = Homogeneous Collection (If Possible)
    AV = GEMWERK_FREIGABE INTRO
    CONCAT_ATTRS = LE LFW LKOM LGAS LAW LWA LWM
    GROUP_BY = BFSNR
    MODE = Geometry - Assemble One Level
    ORDERED = No
    SEP = " "
    SUM = WA GAS KOM AW E WM FW
    AGGREGATE -> AttributeManager_16
AttributeManager_16
    ATTR_TABLE:
      SET_TO WA = FME_CONDITIONAL:DEFAULT_VALUE'1'BOOL_OP;OR;COMPOSITE_TEST;<Unused>;TEST @Value(WA) = 0'2'FME_NUM_CONDITIONS2___
      SET_TO KOM = FME_CONDITIONAL:DEFAULT_VALUE'1'BOOL_OP;OR;COMPOSITE_TEST;<Unused>;TEST @Value(KOM) = 0'2'FME_NUM_CONDITIONS2___
      SET_TO E = FME_CONDITIONAL:DEFAULT_VALUE'1'BOOL_OP;OR;COMPOSITE_TEST;<Unused>;TEST @Value(E) = 0'2'FME_NUM_CONDITIONS2___
      SET_TO AW = FME_CONDITIONAL:DEFAULT_VALUE'1'BOOL_OP;OR;COMPOSITE_TEST;<Unused>;TEST @Value(AW) = 0'2'FME_NUM_CONDITIONS2___
      SET_TO GAS = FME_CONDITIONAL:DEFAULT_VALUE'1'BOOL_OP;OR;COMPOSITE_TEST;<Unused>;TEST @Value(GAS) = 0'2'FME_NUM_CONDITIONS2___
      SET_TO FW = FME_CONDITIONAL:DEFAULT_VALUE'1'BOOL_OP;OR;COMPOSITE_TEST;<Unused>;TEST @Value(FW) = 0'2'FME_NUM_CONDITIONS2___
      SET_TO WM = FME_CONDITIONAL:DEFAULT_VALUE'1'BOOL_OP;OR;COMPOSITE_TEST;<Unused>;TEST @Value(WM) = 0'2'FME_NUM_CONDITIONS2___
      REMOVE MEDIUM_ID
      REMOVE INTRO
      REMOVE DELIVERY_UNIT
      REMOVE FORMAT
      REMOVE FORMAT_ID
      REMOVE WERK_ID
      REMOVE WERK
      REMOVE WERKADDRESS
      REMOVE WERKCITY
      REMOVE WERKK
      REMOVE WERKPHONE
      REMOVE WERKZIP
      REMOVE LIEFERUNG
      REMOVE WERKSTAND
      SET_TO LAW = FME_CONDITIONAL:DEFAULT_VALUE'_FME_NO_OP_'BOOL_OP;AND;COMPOSITE_TEST;<Unused>;TEST @Value(LAW) CONTAINS 3;TEST @Value(LAW) NOT_CONTAINS 2;TEST @Value(LAW) NOT_CONTAINS 1'3'BOOL_OP;AND;COMPOSITE_TEST;<Unused>;TEST @Value(LAW) CONTAINS 3;TEST @Value(LAW) NOT_CONTAINS 1'2'BOOL_OP;AND;COMPOSITE_TEST;<Unused>;TEST @Value(LAW) CONTAINS 3;TEST @Value(LAW) NOT_CONTAINS 2'2'BOOL_OP;OR;COMPOSITE_TEST;<Unused>;TEST LAW ATTRIBUTE_IS_EMPTY _FME_BLANK_STRING_'0'BOOL_OP;OR;COMPOSITE_TEST;<Unused>;TEST @Value(LAW) CONTAINS 2'2'BOOL_OP;OR;COMPOSITE_TEST;<Unused>;TEST @Value(LAW) CONTAINS 1'1'FME_NUM_CONDITIONS7___
      SET_TO LWA = FME_CONDITIONAL:DEFAULT_VALUE'_FME_NO_OP_'BOOL_OP;AND;COMPOSITE_TEST;<Unused>;TEST @Value(LWA) CONTAINS 3;TEST @Value(LWA) NOT_CONTAINS 1;TEST @Value(LWA) NOT_CONTAINS 2'3'BOOL_OP;AND;COMPOSITE_TEST;<Unused>;TEST @Value(LWA) CONTAINS 3;TEST @Value(LWA) NOT_CONTAINS 2'2'BOOL_OP;AND;COMPOSITE_TEST;<Unused>;TEST @Value(LWA) CONTAINS 3;TEST @Value(LWA) NOT_CONTAINS 1'2'BOOL_OP;OR;COMPOSITE_TEST;<Unused>;TEST LWA ATTRIBUTE_IS_EMPTY _FME_BLANK_STRING_'0'BOOL_OP;OR;COMPOSITE_TEST;<Unused>;TEST @Value(LWA) CONTAINS 2'2'BOOL_OP;OR;COMPOSITE_TEST;<Unused>;TEST @Value(LWA) CONTAINS 1'1'FME_NUM_CONDITIONS7___
      SET_TO LE = FME_CONDITIONAL:DEFAULT_VALUE'_FME_NO_OP_'BOOL_OP;AND;COMPOSITE_TEST;<Unused>;TEST @Value(LE) CONTAINS 3;TEST @Value(LE) NOT_CONTAINS 1;TEST @Value(LE) NOT_CONTAINS 2'3'BOOL_OP;AND;COMPOSITE_TEST;<Unused>;TEST @Value(LE) CONTAINS 3;TEST @Value(LE) NOT_CONTAINS 2'2'BOOL_OP;AND;COMPOSITE_TEST;<Unused>;TEST @Value(LE) CONTAINS 3;TEST @Value(LE) NOT_CONTAINS 1'2'BOOL_OP;OR;COMPOSITE_TEST;<Unused>;TEST LE ATTRIBUTE_IS_EMPTY _FME_BLANK_STRING_'0'BOOL_OP;OR;COMPOSITE_TEST;<Unused>;TEST @Value(LE) CONTAINS 2'2'BOOL_OP;OR;COMPOSITE_TEST;<Unused>;TEST @Value(LE) CONTAINS 1'1'FME_NUM_CONDITIONS7___
      SET_TO LGAS = FME_CONDITIONAL:DEFAULT_VALUE'_FME_NO_OP_'BOOL_OP;AND;COMPOSITE_TEST;<Unused>;TEST @Value(LGAS) CONTAINS 3;TEST @Value(LGAS) NOT_CONTAINS 2;TEST @Value(LGAS) NOT_CONTAINS 1'3'BOOL_OP;AND;COMPOSITE_TEST;<Unused>;TEST @Value(LGAS) CONTAINS 3;TEST @Value(LGAS) NOT_CONTAINS 1'2'BOOL_OP;AND;COMPOSITE_TEST;<Unused>;TEST @Value(LGAS) CONTAINS 3;TEST @Value(LGAS) NOT_CONTAINS 2'2'BOOL_OP;OR;COMPOSITE_TEST;<Unused>;TEST LGAS ATTRIBUTE_IS_EMPTY _FME_BLANK_STRING_'0'BOOL_OP;OR;COMPOSITE_TEST;<Unused>;TEST @Value(LGAS) CONTAINS 2'2'BOOL_OP;OR;COMPOSITE_TEST;<Unused>;TEST @Value(LGAS) CONTAINS 1'1'FME_NUM_CONDITIONS7___
      SET_TO LKOM = FME_CONDITIONAL:DEFAULT_VALUE'_FME_NO_OP_'BOOL_OP;AND;COMPOSITE_TEST;<Unused>;TEST @Value(LKOM) CONTAINS 3;TEST @Value(LKOM) NOT_CONTAINS 1;TEST @Value(LKOM) NOT_CONTAINS 2'3'BOOL_OP;AND;COMPOSITE_TEST;<Unused>;TEST @Value(LKOM) CONTAINS 3;TEST @Value(LKOM) NOT_CONTAINS 2'2'BOOL_OP;AND;COMPOSITE_TEST;<Unused>;TEST @Value(LKOM) CONTAINS 3;TEST @Value(LKOM) NOT_CONTAINS 1'2'BOOL_OP;OR;COMPOSITE_TEST;<Unused>;TEST LKOM ATTRIBUTE_IS_EMPTY _FME_BLANK_STRING_'0'BOOL_OP;OR;COMPOSITE_TEST;<Unused>;TEST @Value(LKOM) CONTAINS 2'2'BOOL_OP;OR;COMPOSITE_TEST;<Unused>;TEST @Value(LKOM) CONTAINS 1'1'FME_NUM_CONDITIONS7___
      SET_TO LFW = FME_CONDITIONAL:DEFAULT_VALUE'_FME_NO_OP_'BOOL_OP;AND;COMPOSITE_TEST;<Unused>;TEST @Value(LFW) CONTAINS 3;TEST @Value(LFW) NOT_CONTAINS 1;TEST @Value(LFW) NOT_CONTAINS 2'3'BOOL_OP;AND;COMPOSITE_TEST;<Unused>;TEST @Value(LFW) CONTAINS 3;TEST @Value(LFW) NOT_CONTAINS 2'2'BOOL_OP;AND;COMPOSITE_TEST;<Unused>;TEST @Value(LFW) CONTAINS 3;TEST @Value(LFW) NOT_CONTAINS 1'2'BOOL_OP;OR;COMPOSITE_TEST;<Unused>;TEST LFW ATTRIBUTE_IS_EMPTY _FME_BLANK_STRING_'0'BOOL_OP;OR;COMPOSITE_TEST;<Unused>;TEST @Value(LFW) CONTAINS 2'2'BOOL_OP;OR;COMPOSITE_TEST;<Unused>;TEST @Value(LFW) CONTAINS 1'1'FME_NUM_CONDITIONS7___
      SET_TO LWM = FME_CONDITIONAL:DEFAULT_VALUE'_FME_NO_OP_'BOOL_OP;AND;COMPOSITE_TEST;<Unused>;TEST @Value(LWM) CONTAINS 3;TEST @Value(LWM) NOT_CONTAINS 2;TEST @Value(LWM) NOT_CONTAINS 1'3'BOOL_OP;AND;COMPOSITE_TEST;<Unused>;TEST @Value(LWM) CONTAINS 3;TEST @Value(LWM) NOT_CONTAINS 2'2'BOOL_OP;AND;COMPOSITE_TEST;<Unused>;TEST @Value(LWM) CONTAINS 3;TEST @Value(LWM) NOT_CONTAINS 1'2'BOOL_OP;OR;COMPOSITE_TEST;<Unused>;TEST LWM ATTRIBUTE_IS_EMPTY _FME_BLANK_STRING_'0'BOOL_OP;OR;COMPOSITE_TEST;<Unused>;TEST @Value(LWM) CONTAINS 2'2'BOOL_OP;OR;COMPOSITE_TEST;<Unused>;TEST @Value(LWM) CONTAINS 1'1'FME_NUM_CONDITIONS7___
    -> AttributeManager_20
AttributeManager_20
    ATTR_TABLE = SET_TO LKBESTA = FME_CONDITIONAL:DEFAULT_VALUE'4'BOOL_OP;AND;COMPOSITE_TEST;<Unused>;TEST @Value(LAW) < 1;TEST @Value(LWA) < 1;TEST @Value(LE) < 1;TEST @Value(LGAS) < 1;TEST @Value(LKOM) < 1;TEST @Value(LFW) < 1;TEST @Value(LWM) < 1'0'BOOL_OP;AND;COMPOSITE_TEST;<Unused>;TEST @Value(LAW) < 2;TEST @Value(LWA) < 2;TEST @Value(LE) < 2;TEST @Value(LGAS) < 2;TEST @Value(LKOM) < 2;TEST @Value(LFW) < 2;TEST @Value(LWM) < 2'1'BOOL_OP;AND;COMPOSITE_TEST;<Unused>;TEST @Value(LAW) < 3;TEST @Value(LWA) < 3;TEST @Value(LE) < 3;TEST @Value(LGAS) < 3;TEST @Value(LKOM) < 3;TEST @Value(LFW) < 3;TEST @Value(LWM) < 3'2'BOOL_OP;OR;COMPOSITE_TEST;<Unused>;TEST @Value(LAW) < 3;TEST @Value(LWA) < 3;TEST @Value(LE) < 3;TEST @Value(LGAS) < 3;TEST @Value(LKOM) < 3;TEST @Value(LFW) < 3;TEST @Value(LWM) < 3'3'FME_NUM_CONDITIONS5___
    -> FeatureMerger_3 [REQUESTOR]
    -> FeatureMerger_9 [SUPPLIER]

Bookmark: Übersichts-Layer für LKMAP
FeatureMerger_9
    ATTR_ACCUM_MODE = Merge Supplier
    ATTR_CONFLICT_RES = Use Supplier
    IGNORE_NULLS = No
    JOIN_KEYS = @Value(GMDE) @Value(BFSNR) AUTO
    MERGE_TYPE = Attributes Only
    PROCESS_DUPS = No
    REJECT_NULL_MISSING_KEYS = No
    SUPPLIERS_FIRST = No
    MERGED -> AttributeManager_25
AttributeManager_25
    ATTR_TABLE = RENAME_SET_VALUE LKBESTA > DATASTAND
    -> AttributeManager_24
AttributeManager_24
    ATTR_TABLE = SET_TO DATASTAND = FME_CONDITIONAL:DEFAULT_VALUE'@Value(DATASTAND)'BOOL_OP;OR;COMPOSITE_TEST;<Unused>;TEST @Value(DATASTAND) = 0'4'BOOL_OP;AND;COMPOSITE_TEST;<Unused>;TEST @Value(DATASTAND) = 1;TEST @Value(GEMWERK_FREIGABE) = 0'3'BOOL_OP;AND;COMPOSITE_TEST;<Unused>;TEST @Value(DATASTAND) = 2;TEST @Value(GEMWERK_FREIGABE) = 0'3'FME_NUM_CONDITIONS4___
    -> LKMAP_LKBESTA (writer GEODATABASE_SDE_3)
    -> AttributeManager_26
    -> AttributeManager_34
    -> FeatureJoiner_7 [LEFT]
LKMAP_LKBESTA (writer GEODATABASE_SDE_3)
    attributes: BFSNR smallint, GEMNAME char(50), DATASTAND smallint
AttributeManager_26
    ATTR_TABLE:
      RENAME_SET_VALUE GEMNAME > gemname
      RENAME_SET_VALUE BFSNR > bfsnr
      RENAME_SET_VALUE DATASTAND > datastand
    -> lkmap_lkbesta (writer POSTGIS_1)
Note: PostGIS für Auszählung
lkmap_lkbesta (writer POSTGIS_1)
    attributes: bfsnr int2, gemname varchar(50), datastand int2

Bookmark: Auswertung Projekt
LKBE_STAND_DETAIL (writer GEODATABASE_FILE_1)
    attributes: BFSNR integer, GEMNAME char(50), DATASTAND char(50), MEDIUM_GELIEFERT integer
DATA (writer XLSXW_1)
    attributes: DATE date(10), COUNT_UNIT number(4), COUNT_UNIT_DELIVERED number(5), COUNT_DELIVERY number(5)
LKBE_AUSWERTUNG_LIEFERUNGEN (writer GEODATABASE_FILE_1)
    attributes: BFSNR smallint, GEMNAME char(50), DVSNAME char(50), MEDIUM char(2), C_SENT smallint, C_NOTSENT smallint, C_TOTAL smallint, PERC_SENT float
LKBE_AUSWERTUNG_GEMEINDEN (writer GEODATABASE_FILE_1)
    attributes: BFSNR smallint, GEMNAME char(50), DVSNAME char(50), C_SENT smallint, C_NOTSENT smallint, C_TOTAL smallint, PERC_SENT float

Bookmark: Zeitintervall für Auswertung
TIMELINE (reader XLSXR_3)
    attributes: DATUM_START date, DATUM_END datetime
    -> Tester_9

Bookmark: DVS-Info aus META-DB
SQLCreator
    DATASET = $(LKBE_gpkg)
    EXPOSED_ATTRIBUTE_LIST = BFSNR,DVSKONTAKT,DVSNAME,GEM_ID,INTRO
    FORMAT = SQLITE3
    SQLITE3_QUERY_FEATURE_TYPES_FOR_MERGE_FILTERS = Yes
    SQLITE3_SUPPORT_INTERNATIONALIZATION = YES
    SQL_STATEMENT:
      select m.id as GEM_ID, c.aname as DVSNAME, c.web as DVSKONTAKT, m.bfs as BFSNR, m.introduced as INTRO
      from meta_companies as c, meta_municipalities as m
      WHERE c.Id = m.administrator_id
    RESULT -> AttributeManager_23

Bookmark: LKBESTA setzten
Note: Auswertung mit GEMWERK_FREIGABE & INTRO
AttributeManager_4
    ATTR_TABLE:
      SET_TO AW = FME_CONDITIONAL:DEFAULT_VALUE'_FME_NO_OP_'BOOL_OP;AND;COMPOSITE_TEST;<Unused>;TEST @Value(AW) = 2;TEST @Value(GEMWERK_FREIGABE) = 0'0'FME_NUM_CONDITIONS2___
      SET_TO E = FME_CONDITIONAL:DEFAULT_VALUE'_FME_NO_OP_'BOOL_OP;AND;COMPOSITE_TEST;<Unused>;TEST @Value(E) = 2;TEST @Value(GEMWERK_FREIGABE) = 0'0'FME_NUM_CONDITIONS2___
      SET_TO FW = FME_CONDITIONAL:DEFAULT_VALUE'_FME_NO_OP_'BOOL_OP;AND;COMPOSITE_TEST;<Unused>;TEST @Value(FW) = 2;TEST @Value(GEMWERK_FREIGABE) = 0'0'FME_NUM_CONDITIONS2___
      SET_TO GAS = FME_CONDITIONAL:DEFAULT_VALUE'_FME_NO_OP_'BOOL_OP;AND;COMPOSITE_TEST;<Unused>;TEST @Value(GAS) = 2;TEST @Value(GEMWERK_FREIGABE) = 0'0'FME_NUM_CONDITIONS2___
      SET_TO KOM = FME_CONDITIONAL:DEFAULT_VALUE'_FME_NO_OP_'BOOL_OP;AND;COMPOSITE_TEST;<Unused>;TEST @Value(KOM) = 2;TEST @Value(GEMWERK_FREIGABE) = 0'0'FME_NUM_CONDITIONS2___
      SET_TO WA = FME_CONDITIONAL:DEFAULT_VALUE'_FME_NO_OP_'BOOL_OP;AND;COMPOSITE_TEST;<Unused>;TEST @Value(WA) = 2;TEST @Value(GEMWERK_FREIGABE) = 0'0'FME_NUM_CONDITIONS2___
      SET_TO WM = FME_CONDITIONAL:DEFAULT_VALUE'_FME_NO_OP_'BOOL_OP;AND;COMPOSITE_TEST;<Unused>;TEST @Value(WM) = 2;TEST @Value(GEMWERK_FREIGABE) = 0'0'FME_NUM_CONDITIONS2___
      SET_TO LKBESTA = FME_CONDITIONAL:DEFAULT_VALUE'0'BOOL_OP;AND;COMPOSITE_TEST;<Unused>;TEST @Value(INTRO) > 0;TEST @Value(GEMWERK_FREIGABE) > 0'@Value(LKBESTA)'FME_NUM_CONDITIONS2___
    -> FeatureJoiner_5 [LEFT]
AttributeManager_3
    ATTR_TABLE:
      SET_TO WA = FME_CONDITIONAL:DEFAULT_VALUE'_FME_NO_OP_'BOOL_OP;OR;COMPOSITE_TEST;<Unused>;TEST @Value(WA) = 2'0'FME_NUM_CONDITIONS2___
      SET_TO KOM = FME_CONDITIONAL:DEFAULT_VALUE'_FME_NO_OP_'BOOL_OP;OR;COMPOSITE_TEST;<Unused>;TEST @Value(KOM) = 2'0'FME_NUM_CONDITIONS2___
      SET_TO E = FME_CONDITIONAL:DEFAULT_VALUE'_FME_NO_OP_'BOOL_OP;AND;COMPOSITE_TEST;<Unused>;TEST @Value(E) = 2'0'FME_NUM_CONDITIONS2___
      SET_TO AW = FME_CONDITIONAL:DEFAULT_VALUE'_FME_NO_OP_'BOOL_OP;AND;COMPOSITE_TEST;<Unused>;TEST @Value(AW) = 2'0'FME_NUM_CONDITIONS2___
      SET_TO GAS = FME_CONDITIONAL:DEFAULT_VALUE'_FME_NO_OP_'BOOL_OP;OR;COMPOSITE_TEST;<Unused>;TEST @Value(GAS) = 2'0'FME_NUM_CONDITIONS2___
      SET_TO FW = FME_CONDITIONAL:DEFAULT_VALUE'_FME_NO_OP_'BOOL_OP;AND;COMPOSITE_TEST;<Unused>;TEST @Value(FW) = 2'0'FME_NUM_CONDITIONS2___
      SET_TO WM = FME_CONDITIONAL:DEFAULT_VALUE'_FME_NO_OP_'BOOL_OP;AND;COMPOSITE_TEST;<Unused>;TEST @Value(WM) = 2'0'FME_NUM_CONDITIONS2___
      REMOVE GEM_ID
      REMOVE LAW
      REMOVE LWA
      REMOVE LE
      REMOVE LGAS
      REMOVE LKOM
      REMOVE LFW
      REMOVE LWM
      SET_TO LKBESTA = 0
      SET_TO DVSNAME = -
      SET_TO DVSKONTAKT = -
    -> FeatureJoiner_5 [LEFT]

Bookmark: LKMETA - Norm.sde
LKMETA_WERKMETA (writer GEODATABASE_SDE_3)
    attributes: BFSNR smallint, GEMNAME char(50), DVSNAME char(50), DVSKONTAKT char(255), MEDIUM char(3), WERK char(50), WERKK char(255), WERKORT char(255), WERKSTAND smallint, ANGFORMAT smallint, LIEFERUNG smallint, LIEFERDATE date, LIEFERID integer
LKMETA_STAND (writer GEODATABASE_SDE_3)
    attributes: BFSNR smallint, GEMNAME char(50), JAHRPLAN smallint, DVSNAME char(50), DVSKONTAKT char(255), AW smallint, E smallint, FW smallint, GAS smallint, KOM smallint, WA smallint, WM smallint, LKBESTA smallint

Bookmark: Geplantes Jahr der Einführung
Traking_Gemeinden_2020 (reader XLSXR_2)
    attributes: BFSNR number(4,0), GEMEINDE char(28), ständige Bev. char(7), Fläche _ha_ number(14,8), geplantes Jahr char(6), definitives Jahr number(5,0), Jahr für LKMETA number(5,0), Rückmeldung erhalten date, Rückmeldung (Freitext) char(57), Jahr ohne Rückmeldung number(5,0), Einwohner ohne Rückmeldung number(5,0), Fläche ohne Rückmeldung number(14,8), Kategorie Statistik Einführung char(20), DVS char(30), Vertrag string, Kontakt Gemeinde char(34), Mail an  Gemeinde date, R string, S string, T string, U string, V string
    -> AttributeManager
