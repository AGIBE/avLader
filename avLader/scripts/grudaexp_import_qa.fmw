FME workspace grudaexp_import_qa.fmw

Parameters:
- QA_EXCEL =   # Destination Microsoft Excel File
- LOGFILE =
- NORM_DATABASE =   # Norm-Database
- NORM_PASSWORD =   # Norm-Passwort
- NORM_USERNAME =   # Norm-Username
- VEK1_DATABASE =   # Vek1-Database
- VEK1_PASSWORD =   # Vek1-Password
- VEK1_USERNAME =   # Vek1-Username

Writers:
- XLS_ADO_1: XLS_ADO to $(QA_EXCEL)

Note: VEK1P
SQLCreator
    DATASET = $(VEK1_DATABASE)
    EXPOSED_ATTRIBUTE_LIST = BFSNR,GBKRNR,ANZAHL
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select t.bfsnr, t.gbkrnr, count(*) anzahl from geodb.grudaexp_grudagst t group by t.bfsnr, t.gbkrnr order by t.bfsnr asc, t.gbkrnr asc
    RESULT -> StringConcatenator
StringConcatenator
    ACTION = Create New Attribute
    PARM_LINE = @Value(BFSNR)@Value(GBKRNR)
    VAL_ATTR = TEMPKEY
    -> BulkAttributeRenamer
BulkAttributeRenamer
    ATTRCHOICE = All Attributes
    MODE_CHOICE = RENAME
    PATTERN_ACTION_DISP = ADDSUFFIX
    REPLACE_STR = _ALT
    -> FeatureMerger [REQUESTOR]
Note: TEAMP
SQLCreator_2
    DATASET = $(NORM_DATABASE)
    EXPOSED_ATTRIBUTE_LIST = BFSNR,GBKRNR,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select t.bfsnr, t.gbkrnr, count(*) anzahl from grudaexp_grudagst t group by t.bfsnr, t.gbkrnr order by t.bfsnr asc, t.gbkrnr asc
    RESULT -> StringConcatenator_2
StringConcatenator_2
    ACTION = Create New Attribute
    PARM_LINE = @Value(BFSNR)@Value(GBKRNR)
    VAL_ATTR = TEMPKEY
    -> BulkAttributeRenamer_2
BulkAttributeRenamer_2
    ATTRCHOICE = All Attributes
    MODE_CHOICE = RENAME
    PATTERN_ACTION_DISP = ADDSUFFIX
    REPLACE_STR = _NEU
    -> FeatureMerger [SUPPLIER]
FeatureMerger
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator
    UNMERGED_REQUESTOR -> GRUDAGST_verschwunden (writer XLS_ADO_1)
    UNUSED_SUPPLIER -> GRUDAGST_hinzugekommen (writer XLS_ADO_1)
ExpressionEvaluator
    ACTION = Create New Attribute
    EXPRESSION = (@Value(ANZAHL_NEU)-@Value(ANZAHL_ALT))
    VAL_ATTR = DIFF_ABS
    -> ExpressionEvaluator_2
ExpressionEvaluator_2
    ACTION = Create New Attribute
    EXPRESSION = (@Value(DIFF_ABS)/(@Value(ANZAHL_ALT)/100.0))
    VAL_ATTR = DIFF_REL
    -> Sorter
Sorter
    SORT_PARM = DIFF_ABS NUMERIC ASCENDING
    SORTED -> GRUDAGST_unveraendert (writer XLS_ADO_1)
GRUDAGST_unveraendert (writer XLS_ADO_1)
    attributes: BFSNR double, GBKRNR double, ANZAHL_ALT double, ANZAHL_NEU double, DIFF_ABS double, DIFF_REL decimal(30,4)
GRUDAGST_verschwunden (writer XLS_ADO_1)
    attributes: BFSNR double, GBKRNR double, ANZAHL double
GRUDAGST_hinzugekommen (writer XLS_ADO_1)
    attributes: BFSNR double, GBKRNR double, ANZAHL double
Note: VEK1P
SQLCreator_15
    DATASET = $(VEK1_DATABASE)
    EXPOSED_ATTRIBUTE_LIST = ANZAHL_ALT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select count(*) anzahl_alt from geodb.grudaexp_grudageb
    RESULT -> AttributeCreator
AttributeCreator
    ATTR_TABLE = SET_TO joinfeld = 1
    -> FeatureMerger_5 [REQUESTOR]
Note: TEAMP
SQLCreator_16
    DATASET = $(NORM_DATABASE)
    EXPOSED_ATTRIBUTE_LIST = ANZAHL_NEU
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select count(*) anzahl_neu from grudaexp_grudageb
    RESULT -> AttributeCreator_2
AttributeCreator_2
    ATTR_TABLE = SET_TO joinfeld = 1
    -> FeatureMerger_5 [SUPPLIER]
FeatureMerger_5
    ATTR_ACCUM_MODE = Merge Supplier
    ATTR_CONFLICT_RES = Use Requestor
    IGNORE_NULLS = Yes
    JOIN_KEYS = @Value(joinfeld) @Value(joinfeld) AUTO
    MERGE_TYPE = Attributes Only
    PROCESS_DUPS = NO
    REJECT_NULL_MISSING_KEYS = No
    SUPPLIERS_FIRST = No
    MERGED -> ExpressionEvaluator_3
ExpressionEvaluator_3
    ACTION = Create New Attribute
    EXPRESSION = (@Value(ANZAHL_NEU)-@Value(ANZAHL_ALT))
    VAL_ATTR = DIFF_ABS
    -> GRUDAGEB_anzahl (writer XLS_ADO_1)
GRUDAGEB_anzahl (writer XLS_ADO_1)
    attributes: ANZAHL_ALT double, ANZAHL_NEU double, DIFF_ABS double
Note: VEK1P
SQLCreator_3
    DATASET = $(VEK1_DATABASE)
    EXPOSED_ATTRIBUTE_LIST = ANZAHL_ALT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select count(*) anzahl_alt from geodb.grudaexp_grudagzg
    RESULT -> AttributeCreator_3
AttributeCreator_3
    ATTR_TABLE = SET_TO joinfeld = 1
    -> FeatureMerger_2 [REQUESTOR]
Note: TEAMP
SQLCreator_7
    DATASET = $(NORM_DATABASE)
    EXPOSED_ATTRIBUTE_LIST = ANZAHL_NEU
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select count(*) anzahl_neu from grudaexp_grudagzg
    RESULT -> AttributeCreator_4
AttributeCreator_4
    ATTR_TABLE = SET_TO joinfeld = 1
    -> FeatureMerger_2 [SUPPLIER]
FeatureMerger_2
    ATTR_ACCUM_MODE = Merge Supplier
    ATTR_CONFLICT_RES = Use Requestor
    IGNORE_NULLS = Yes
    JOIN_KEYS = @Value(joinfeld) @Value(joinfeld) AUTO
    MERGE_TYPE = Attributes Only
    PROCESS_DUPS = NO
    REJECT_NULL_MISSING_KEYS = No
    SUPPLIERS_FIRST = No
    MERGED -> ExpressionEvaluator_4
ExpressionEvaluator_4
    ACTION = Create New Attribute
    EXPRESSION = (@Value(ANZAHL_NEU)-@Value(ANZAHL_ALT))
    VAL_ATTR = DIFF_ABS
    -> GRUDAGZG (writer XLS_ADO_1)
GRUDAGZG (writer XLS_ADO_1)
    attributes: ANZAHL_ALT double, ANZAHL_NEU double, DIFF_ABS double
Note: VEK1P
SQLCreator_8
    DATASET = $(VEK1_DATABASE)
    EXPOSED_ATTRIBUTE_LIST = ANZAHL_ALT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select count(*) anzahl_alt from geodb.grudaexp_grudabbf
    RESULT -> AttributeCreator_5
AttributeCreator_5
    ATTR_TABLE = SET_TO joinfeld = 1
    -> FeatureMerger_3 [REQUESTOR]
Note: TEAMP
SQLCreator_9
    DATASET = $(NORM_DATABASE)
    EXPOSED_ATTRIBUTE_LIST = ANZAHL_NEU
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select count(*) anzahl_neu from grudaexp_grudabbf
    RESULT -> AttributeCreator_6
AttributeCreator_6
    ATTR_TABLE = SET_TO joinfeld = 1
    -> FeatureMerger_3 [SUPPLIER]
FeatureMerger_3
    ATTR_ACCUM_MODE = Merge Supplier
    ATTR_CONFLICT_RES = Use Requestor
    IGNORE_NULLS = Yes
    JOIN_KEYS = @Value(joinfeld) @Value(joinfeld) AUTO
    MERGE_TYPE = Attributes Only
    PROCESS_DUPS = NO
    REJECT_NULL_MISSING_KEYS = No
    SUPPLIERS_FIRST = No
    MERGED -> ExpressionEvaluator_5
ExpressionEvaluator_5
    ACTION = Create New Attribute
    EXPRESSION = (@Value(ANZAHL_NEU)-@Value(ANZAHL_ALT))
    VAL_ATTR = DIFF_ABS
    -> GRUDABBF (writer XLS_ADO_1)
GRUDABBF (writer XLS_ADO_1)
    attributes: ANZAHL_ALT double, ANZAHL_NEU double, DIFF_ABS double
Note: VEK1P
SQLCreator_10
    DATASET = $(VEK1_DATABASE)
    EXPOSED_ATTRIBUTE_LIST = ANZAHL_ALT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select count(*) anzahl_alt from geodb.grudaexp_grudagad
    RESULT -> AttributeCreator_7
AttributeCreator_7
    ATTR_TABLE = SET_TO joinfeld = 1
    -> FeatureMerger_4 [REQUESTOR]
Note: TEAMP
SQLCreator_11
    DATASET = $(NORM_DATABASE)
    EXPOSED_ATTRIBUTE_LIST = ANZAHL_NEU
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select count(*) anzahl_neu from grudaexp_grudagad
    RESULT -> AttributeCreator_8
AttributeCreator_8
    ATTR_TABLE = SET_TO joinfeld = 1
    -> FeatureMerger_4 [SUPPLIER]
FeatureMerger_4
    ATTR_ACCUM_MODE = Merge Supplier
    ATTR_CONFLICT_RES = Use Requestor
    IGNORE_NULLS = Yes
    JOIN_KEYS = @Value(joinfeld) @Value(joinfeld) AUTO
    MERGE_TYPE = Attributes Only
    PROCESS_DUPS = NO
    REJECT_NULL_MISSING_KEYS = No
    SUPPLIERS_FIRST = No
    MERGED -> ExpressionEvaluator_6
ExpressionEvaluator_6
    ACTION = Create New Attribute
    EXPRESSION = (@Value(ANZAHL_NEU)-@Value(ANZAHL_ALT))
    VAL_ATTR = DIFF_ABS
    -> GRUDAGAD (writer XLS_ADO_1)
GRUDAGAD (writer XLS_ADO_1)
    attributes: ANZAHL_ALT double, ANZAHL_NEU double, DIFF_ABS double
Note: TEAMP
SQLCreator_12
    COORDSYS = $(NORM_DATABASE)
    DATASET = teamp
    EXPOSED_ATTRIBUTE_LIST = BEGID,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.kant_gid begid, count(*) anzahl
        from grudaexp_grudageb t
          group by t.kant_gid
          having count(*) > 1
      order by t.kant_gid
    RESULT -> GRUDAGEB_BEGID_doppelt (writer XLS_ADO_1)
GRUDAGEB_BEGID_doppelt (writer XLS_ADO_1)
    attributes: BEGID double, ANZAHL double
Note: TEAMP
SQLCreator_13
    DATASET = $(NORM_DATABASE)
    EXPOSED_ATTRIBUTE_LIST = GWR_EGID,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.gwr_egid gwr_egid, count(*) anzahl
        from grudaexp_grudageb t
          group by t.gwr_egid
          having count(*) > 1
      order by t.gwr_egid
    RESULT -> GRUDAGEB_EGID_doppelt (writer XLS_ADO_1)
GRUDAGEB_EGID_doppelt (writer XLS_ADO_1)
    attributes: GWR_EGID double, ANZAHL double
SQLCreator_18
    DATASET = $(NORM_DATABASE)
    EXPOSED_ATTRIBUTE_LIST = GST_ID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select bbf.gst_id from norm.grudaexp_grudabbf bbf left outer join norm.grudaexp_grudagst gst on bbf.gst_id=gst.gst_id where gst.gst_id is null
    RESULT -> Kein_BBF_zu_GST (writer XLS_ADO_1)
Kein_BBF_zu_GST (writer XLS_ADO_1)
    attributes: GST_ID varchar(200)
SQLCreator_19
    DATASET = $(NORM_DATABASE)
    EXPOSED_ATTRIBUTE_LIST = GEB_ID,GST_ID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select gzg.geb_id, gzg.gst_id from norm.grudaexp_grudagzg gzg left outer join norm.grudaexp_grudagst gst on gzg.gst_id=gst.gst_id where gst.gst_id is null
    RESULT -> Kein_GST_zu_GEB_via_GZG (writer XLS_ADO_1)
Kein_GST_zu_GEB_via_GZG (writer XLS_ADO_1)
    attributes: GEB_ID varchar(200), GST_ID varchar(200)
SQLCreator_17
    DATASET = $(NORM_DATABASE)
    EXPOSED_ATTRIBUTE_LIST = GEB_ID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select geb.geb_id from norm.grudaexp_grudageb geb left outer join norm.grudaexp_grudagzg gzg on geb.geb_id=gzg.geb_id where gzg.geb_id is null
    RESULT -> GEB_hat_kein_GZG (writer XLS_ADO_1)
GEB_hat_kein_GZG (writer XLS_ADO_1)
    attributes: GEB_ID varchar(200)
SQLCreator_6
    DATASET = $(NORM_DATABASE)
    EXPOSED_ATTRIBUTE_LIST = GEB_ID,GST_ID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select gzg.geb_id, gzg.gst_id from norm.grudaexp_grudagzg gzg left outer join norm.grudaexp_grudageb geb on gzg.geb_id=geb.geb_id where geb.geb_id is null
    RESULT -> GZG_findet_kein_GEB (writer XLS_ADO_1)
GZG_findet_kein_GEB (writer XLS_ADO_1)
    attributes: GEB_ID varchar(200), GST_ID varchar(200)
SQLCreator_5
    DATASET = $(NORM_DATABASE)
    EXPOSED_ATTRIBUTE_LIST = GEB_ID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select geb.geb_id from norm.grudaexp_grudageb geb left outer join norm.grudaexp_grudagad gad on geb.geb_id=gad.geb_id where gad.geb_id is null
    RESULT -> GEB_ohne_GAD (writer XLS_ADO_1)
GEB_ohne_GAD (writer XLS_ADO_1)
    attributes: GEB_ID varchar(200)
