FME workspace oereb_liegenschaften.fmw

Parameters:
- TEAM_CONNECTIONFILE =
- TEAM_USERNAME =   # Team-Username
- TEAM_PASSWORD =   # Team-Passwort
- TEAM_DATABASE =   # Team-Database
- LOGFILE =   # Logfile
- GEODB_PG_DATABASE =
- GEODB_PG_USERNAME =
- GEODB_PG_PASSWORD =
- GEODB_PG_HOST =
- GEODB_PG_PORT =
- VEK2_CONNECTIONFILE =
- WHERE_CLAUSE =
- AV_DATE =   # "{}" AV_DATE
- OEREB_PG_DATABASE =
- OEREB_PG_HOST =
- OEREB_PG_PASSWORD =
- OEREB_PG_PORT =
- OEREB_PG_USERNAME =
- PG_DB = work
- PG_HOST = a4pu-db-oereb01.infra.be.ch
- PG_PASSWORD =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
- PG_PORT = 12880
- PG_USERNAME = oereb

Readers:
- GEODATABASE_SDE_1: GEODATABASE_SDE
- GEODATABASE_SDE_2: GEODATABASE_SDE

Writers:
- POSTGIS_3: POSTGIS to $(OEREB_PG_DATABASE)
- POSTGIS_2: POSTGIS to $(GEODB_PG_DATABASE)
- GEODATABASE_SDE_3: GEODATABASE_SDE

Note: NORM.DIPANU_DIPANUF
DIPANU_DIPANUF (reader GEODATABASE_SDE_1)
    attributes: OBJECTID integer, NBIDENT char(12), BFSNR smallint, GEMNAME char(60), GBKR smallint, GBKRNAME char(60), EGRID char(14), GSTNR integer, GSTART smallint, GSTBEZ char(12), GBFLAE integer, TECHFLAE double, QV smallint, GZSTAT smallint, GZNR char(20), PROJSTAT smallint, MITGEOM smallint, SPRACHE smallint, UNVERBI smallint, LETZTEAEND char(10), GENGBKRI integer, GENGBKRN char(50), SHAPE.AREA double, SHAPE.LEN double
    -> AttributeRemover
AttributeRemover
    REMOVE_ATTRS = SPRACHE,SHAPE.LEN,GZSTAT,LETZTEAEND,QV,PROJSTAT,GENGBKRN,GSTBEZ,MITGEOM,geodb_oid,SHAPE.AREA,GZNR,UNVERBI,GENGBKRI,OBJECTID
    -> AttributeCreator
AttributeCreator
    ATTR_TABLE = SET_TO OEREBSTATUS = public
    -> AttributeRenamer
AttributeRenamer
    ATTR_TABLE:
      RENAME_SET_DEFAULT GSTNR > NUMMER
      RENAME_SET_DEFAULT GBFLAE > GBFLAECHE
      RENAME_SET_DEFAULT GBKR > KREIS
      RENAME_SET_DEFAULT GSTART > ART
    -> AttributeFilter
AttributeFilter
    ATTR_NAME = KREIS
    ATTR_VALUES = <EMPTY>,<MISSING>,<NULL>,<UNFILTERED>,0
    <UNFILTERED> -> StringConcatenator
    0 -> AttributeCreator_2
StringConcatenator
    ACTION = Create New Attribute
    PARM_LINE = @Value(KREIS) - @Value(GBKRNAME)
    VAL_ATTR = KREISBEZ
    -> StringConcatenator_2
StringConcatenator_2
    ACTION = Create New Attribute
    PARM_LINE = @Value(GEMNAME) (@Value(KREISBEZ))
    VAL_ATTR = GEMKR_NAME
    -> AttributeRemover_2
AttributeCreator_2
    ATTR_TABLE = SET_TO KREISBEZ = FME_NULL_VALUE
    -> AttributeCreator_5
AttributeCreator_5
    ATTR_TABLE = SET_TO GEMKR_NAME = @Value(GEMNAME)
    -> AttributeRemover_2
AttributeRemover_2
    REMOVE_ATTRS = GBKRNAME
    -> FeatureMerger [REQUESTOR]
Note: GEODB.GBKREIS_GBKR
GBKREIS_GBKR (reader GEODATABASE_SDE_2)
    attributes: OBJECTID integer, KT smallint, GMDE smallint, NAME char(31), KREIS smallint, KR_BEZ char(60), SHAPE.AREA double, SHAPE.LEN double
    -> AttributeCreator_3
AttributeCreator_3
    ATTR_TABLE = SET_TO OEREBSTATUS = public
    -> Tester
Tester
    BOOL_OP = OR
    TEST_CLAUSE = TEST @Value(KREIS) > 0
    PASSED -> StringConcatenator_4
    FAILED -> AttributeCopier
StringConcatenator_4
    ACTION = Create New Attribute
    PARM_LINE = @Value(KREIS) - @Value(KR_BEZ)
    VAL_ATTR = KREISNAME
    -> AttributeRemover_4
AttributeCopier
    ATTR_TABLE = COPY KR_BEZ > KREISNAME
    -> AttributeRemover_4
AttributeRemover_4
    REMOVE_ATTRS = geodb_oid,OBJECTID,KT,KR_BEZ,SHAPE.AREA,SHAPE.LEN
    -> AttributeRenamer_4
AttributeRenamer_4
    ATTR_TABLE:
      RENAME_SET_DEFAULT GMDE > BFSNR
      RENAME_SET_DEFAULT KREIS > KREISNR
    -> Aggregator_2
Aggregator_2
    ACCUM_ATTRS_NAME = Drop Incoming Attributes
    AGGREGATE_TYPE = Homogeneous Collection (If Possible)
    GROUP_BY = BFSNR NAME KREISNR KREISNAME OEREBSTATUS
    MODE = Geometry - Assemble One Level
    ORDERED = No
    SEP = ,
    AGGREGATE -> TestFilter
TestFilter
    DEFAULT_VALUE = <UNFILTERED>
    TEST_LIST = BOOL_OP,OR,COMPOSITE_TEST,<Unused>,TEST_CLAUSE,"TEST @Value(KREISNR) > 0",MITKREIS
    MITKREIS -> StringConcatenator_3
    <UNFILTERED> -> AttributeCreator_4
StringConcatenator_3
    ACTION = Create New Attribute
    PARM_LINE = @Value(NAME) (@Value(KREISNAME))
    VAL_ATTR = GEMKR_NAME
    -> FeatureHolder
AttributeCreator_4
    ATTR_TABLE = SET_TO GEMKR_NAME = @Value(NAME)
    -> FeatureHolder
FeatureHolder
    -> BulkAttributeRenamer_2
    -> OEREB_GBKREIS (writer GEODATABASE_SDE_3)
Note: GEODB.OEREB_GBKREIS
OEREB_GBKREIS (writer GEODATABASE_SDE_3)
    attributes: BFSNR smallint, NAME char(50), KREISNR smallint, KREISNAME char(60), GEMKR_NAME char(100), OEREBSTATUS char(6)
BulkAttributeRenamer_2
    ATTRCHOICE = All Attributes
    CASE_CHANGE_TYPE = lower
    MODE_CHOICE = RENAME
    PATTERN_ACTION_DISP = CASECHANGE
    -> Counter_2
Counter_2
    CNT_ATTR = objectid
    DOMAIN = gbkreis_counter
    SCOPE = Global
    START = 1
    -> oereb_gbkreis (writer POSTGIS_2)
Note: geodb.oereb_gbkreis
oereb_gbkreis (writer POSTGIS_2)
    attributes: objectid int4,PRIKEY, bfsnr int2,BTREE, name varchar(50), kreisnr int2,BTREE, kreisname varchar(60), gemkr_name varchar(100), oerebstatus varchar(6),BTREE
DIPANU_GSTARTT (reader GEODATABASE_SDE_1)
    attributes: OBJECTID integer, GSTART smallint, GSTARTDE char(2), GSTARTFR char(2), BEZ_DE char(50), BEZ_FR char(50)
    -> AttributeRemover_3
AttributeRemover_3
    REMOVE_ATTRS = geodb_oid,GSTARTFR,GSTARTDE,OBJECTID
    -> AttributeRenamer_3
AttributeRenamer_3
    ATTR_TABLE:
      RENAME_SET_DEFAULT GSTART > ART
      RENAME_SET_DEFAULT BEZ_DE > ARTDE
      RENAME_SET_DEFAULT BEZ_FR > ARTFR
    -> FeatureMerger [SUPPLIER]
FeatureMerger
    ATTR_ACCUM_MODE = Merge Supplier
    ATTR_CONFLICT_RES = Use Requestor
    IGNORE_NULLS = Yes
    JOIN_KEYS = @Value(ART) @Value(ART) AUTO
    MERGE_TYPE = Attributes Only
    PROCESS_DUPS = NO
    REJECT_NULL_MISSING_KEYS = No
    SUPPLIERS_FIRST = No
    MERGED -> FeatureMerger_2 [REQUESTOR]
Note: Grundbuchfläche aus MOPUBE_LIF / holen (s. #131)
SQLCreator
    DATASET = $(TEAM_DATABASE)
    EXPOSED_ATTRIBUTE_LIST = EGRID,LIF_GBFLAE
    FORMAT = ORACLE_NONSPATIAL
    ORACLE_NONSPATIAL_PASSWORD = $(TEAM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(TEAM_USERNAME)
    ORACLE_NONSPATIAL_USE_UNIFIED_DATE_ATTRS = YES
    SQL_STATEMENT = select egrid, sum(flaechmass) lif_gbflae from NORM.MOPUBE_LIF where egrid in (select egrid from NORM.GRUDAEXP_GRUDAGST where gueltigkei=1) group by egrid
    RESULT -> FeatureMerger_2 [SUPPLIER]
Note: Grundbuchfläche aus MOPUBE_LISRF / holen (s. #131)
SQLCreator_2
    DATASET = $(TEAM_DATABASE)
    EXPOSED_ATTRIBUTE_LIST = EGRID,LIF_GBFLAE
    FORMAT = ORACLE_NONSPATIAL
    ORACLE_NONSPATIAL_PASSWORD = $(TEAM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(TEAM_USERNAME)
    ORACLE_NONSPATIAL_USE_UNIFIED_DATE_ATTRS = YES
    SQL_STATEMENT = select egrid, sum(flaechmass) lif_gbflae from NORM.MOPUBE_LISRF where egrid in (select egrid from NORM.GRUDAEXP_GRUDAGST where gueltigkei=1) group by egrid
    RESULT -> FeatureMerger_2 [SUPPLIER]
FeatureMerger_2
    ATTR_ACCUM_MODE = Merge Supplier
    ATTR_CONFLICT_RES = Use Requestor
    IGNORE_NULLS = No
    JOIN_KEYS = @Value(EGRID) @Value(EGRID) AUTO
    MERGE_TYPE = Attributes Only
    PROCESS_DUPS = NO
    REJECT_NULL_MISSING_KEYS = No
    SUPPLIERS_FIRST = No
    MERGED -> AttributeRemover_5
    UNMERGED_REQUESTOR -> BulkAttributeRenamer
    UNMERGED_REQUESTOR -> OEREB_LIEGENSCHAFTEN (writer GEODATABASE_SDE_3)
    UNMERGED_REQUESTOR -> FeatureMerger_3 [REQUESTOR]
AttributeRemover_5
    REMOVE_ATTRS = GBFLAECHE
    -> AttributeRenamer_5
AttributeRenamer_5
    ATTR_TABLE = RENAME_SET_DEFAULT LIF_GBFLAE > GBFLAECHE
    -> BulkAttributeRenamer
    -> OEREB_LIEGENSCHAFTEN (writer GEODATABASE_SDE_3)
    -> FeatureMerger_3 [REQUESTOR]
Note: GEODB.OEREB_LIEGENSCHAFTEN
OEREB_LIEGENSCHAFTEN (writer GEODATABASE_SDE_3)
    attributes: NUMMER char(255), EGRID char(14), BFSNR smallint, KREIS smallint, NBIDENT char(255), KANTON char(100), METAGEO_DE char(1023), METAGEO_FR char(1023), GEMKR_NAME char(100), OEREBSTATUS char(10), GBFLAECHE integer, KREISBEZ char(60), ART smallint, ARTDE char(30), ARTFR char(30), TECHFLAE double
BulkAttributeRenamer
    ATTRCHOICE = All Attributes
    CASE_CHANGE_TYPE = lower
    MODE_CHOICE = RENAME
    PATTERN_ACTION_DISP = CASECHANGE
    -> Counter
Counter
    CNT_ATTR = objectid
    DOMAIN = liegenschaften_counter
    SCOPE = Global
    START = 1
    -> oereb_liegenschaften (writer POSTGIS_2)
Note: geodb.oereb_liegenschaften
oereb_liegenschaften (writer POSTGIS_2)
    attributes: objectid int4,PRIKEY, nummer varchar(255),BTREE, egrid varchar(14),BTREE, bfsnr int2,BTREE, kreis int2,BTREE, nbident varchar(255), kanton varchar(100), metageo_de varchar(1023), metageo_fr varchar(1023), gemkr_name varchar(100), oerebstatus varchar(10),BTREE, gbflaeche int4, kreisbez varchar(60), art int2, artde varchar(30), artfr varchar(30), techflae numeric(12,3)
MOPUBE_LIF (reader GEODATABASE_SDE_1)
    attributes: OBJECTID integer, LIFID char(32), NUMMER char(15), EGRID char(14), VOLLSTAEND integer, FLAECHMASS integer, GUELTEINTR date, BFSNR integer, GBKR integer, NBIDENT char(12), SHAPE.AREA double, SHAPE.LEN double
    -> AttributeKeeper
MOPUBE_LISRF (reader GEODATABASE_SDE_1)
    attributes: OBJECTID integer, LISRFID char(32), NUMMER char(15), EGRID char(14), ART integer, VOLLSTAEND integer, FLAECHMASS integer, GUELTEINTR date, BFSNR integer, GBKR integer, NBIDENT char(12), SHAPE.AREA double, SHAPE.LEN double
    -> AttributeKeeper
AttributeKeeper
    KEEP_ATTRS = EGRID
    -> Aggregator
Aggregator
    ACCUM_ATTRS_NAME = Use Attributes From One Feature
    AGGREGATE_TYPE = Homogeneous Collection (If Possible)
    GROUP_BY = EGRID
    MODE = Geometry - Assemble One Level
    ORDERED = No
    SEP = ,
    AGGREGATE -> GeometryExtractor
GeometryExtractor
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = Yes
    -> FeatureMerger_3 [SUPPLIER]
FeatureMerger_3
    ATTR_ACCUM_MODE = Merge Supplier
    ATTR_CONFLICT_RES = Use Requestor
    IGNORE_NULLS = No
    JOIN_KEYS = @Value(EGRID) @Value(EGRID) AUTO
    MERGE_TYPE = Attributes Only
    PROCESS_DUPS = NO
    REJECT_NULL_MISSING_KEYS = No
    SUPPLIERS_FIRST = No
    MERGED -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> ArcStroker
ArcStroker
    MAKE_POLY = No
    NUM = 100
    STROKE_CHOICE = Number of Interpolated Edges
    STROKED -> GeometryRefiner
GeometryRefiner
    -> JSONTemplater_10 [ROOT]
Note: date_provider-Attribut als / JSON-String aufbauen.
JSONTemplater_10
    RESULT_ATTRIBUTE = data_provider
    ROOT_QUERY_EXPR:
      {
          "fr": "Office de l'information géographique",
          "de": "Amt für Geoinformation"
      }
    VISIBLE_QUERY_VALIDATE = Yes
    -> AttributeRenamer_6
AttributeRenamer_6
    ATTR_TABLE:
      RENAME_SET_DEFAULT NBIDENT > identdn
      RENAME_SET_DEFAULT NUMMER > number
      RENAME_SET_DEFAULT EGRID > egrid
      RENAME_SET_DEFAULT BFSNR > fosnr
      RENAME_SET_DEFAULT GBFLAECHE > land_registry_area
      RENAME_SET_DEFAULT ARTDE > type
      RENAME_SET_DEFAULT GEMNAME > municipality
      RENAME_SET_DEFAULT KREISBEZ > subunit_of_land_register
    -> Counter_3
Counter_3
    CNT_ATTR = id
    DOMAIN = counter
    SCOPE = Global
    START = 1
    -> real_estate (writer POSTGIS_3)
real_estate (writer POSTGIS_3)
    attributes: id int4,PrimaryKey, identdn varchar(80), number varchar(80), egrid varchar(80), type varchar(80), canton varchar(80), municipality varchar(80), subunit_of_land_register varchar(80), fosnr int4, metadata_of_geographical_base_data varchar(80), land_registry_area int4, currentness date, data_provider json
