FME workspace lk_import_2.fmw

Parameters:
- SourceDataset_XLSXR = \\B3012FIL002\GIS01\z_datauf\GIS_Prod\LKMAP\work\tabelle\LKMAP_Wertetabellen.xlsx   # Source Microsoft Excel File(s)
- LKBE_gpkg = \\geodb.infra.be.ch\arbeit\Rampe\LKMAP\gpkg\LKMap_be.gpkg   # Geopackage LKBE
- LOGFILE =
- POSTGIS_DB = team   # Database
- POSTGIS_HOST = a4pa-dl-oereb01.infra.be.ch   # Host
- POSTGIS_PASSWORD =   # Password
- POSTGIS_PORT = 12890   # Port
- POSTGIS_USER = norm   # Username
- NORM_CONNECTIONFILE = \\geodb.infra.be.ch\arbeit\Anwend\connections\PROD\norm@team.sde   # Connection File

Readers:
- XLSXR_1: XLSXR from $(SourceDataset_XLSXR)
- GEOPACKAGE_1: GEOPACKAGE from $(LKBE_gpkg) in CH1903Plus_1.LV95/01

Writers:
- POSTGIS_1: POSTGIS to $(POSTGIS_DB)
- POSTGRES_1: POSTGRES to $(POSTGIS_DB)
- GEODATABASE_SDE_1: GEODATABASE_SDE

LKBE_Standard_flaeche_2
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_AWPG (writer GEODATABASE_SDE_1)
    AttributeManager_2_Output -> AttributeManager_13
LKBE_Standard_flaeche_3
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_EPG (writer GEODATABASE_SDE_1)
    AttributeManager_2_Output -> AttributeManager_14
LKBE_Standard_flaeche
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_FWPG (writer GEODATABASE_SDE_1)
    AttributeManager_2_Output -> AttributeManager_15
LKBE_Standard_flaeche_4
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_GASPG (writer GEODATABASE_SDE_1)
    AttributeManager_2_Output -> AttributeManager_16
LKBE_Standard_flaeche_5
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_KOMPG (writer GEODATABASE_SDE_1)
    AttributeManager_2_Output -> AttributeManager_17
LKBE_Standard_flaeche_6
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_WAPG (writer GEODATABASE_SDE_1)
    AttributeManager_2_Output -> AttributeManager_18
LKBE_Standard_flaeche_7
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_2_Output -> LKMAP_WMPG (writer GEODATABASE_SDE_1)
    AttributeManager_2_Output -> AttributeManager_19
LKBE_Standard_linie
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_11
Tester_11
    BOOL_OP = OR
    TEST_CLAUSE = TEST @Value(OBJCODE) CONTAINS .Fernwirkkabel
    PASSED -> LKMAP_AWFWK (writer GEODATABASE_SDE_1)
    PASSED -> AttributeManager_20
    FAILED -> LKMAP_AWPL (writer GEODATABASE_SDE_1)
    FAILED -> AttributeManager_21
LKBE_Standard_linie_2
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> AttributeManager
AttributeManager
    ATTR_TABLE = SET_TO BREITESYMB = FME_CONDITIONAL:DEFAULT_VALUE'_FME_NO_OP_'BOOL_OP;OR;COMPOSITE_TEST;<Unused>;TEST @Value(OBJCODE) = Elektrizitaet.AnkerStrebe'3'FME_NUM_CONDITIONS2___
    -> LKMAP_EPL (writer GEODATABASE_SDE_1)
    -> AttributeManager_22
LKBE_Standard_linie_3
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_9
Tester_9
    BOOL_OP = OR
    TEST_CLAUSE = TEST @Value(OBJCODE) CONTAINS .Fernwirkkabel
    PASSED -> LKMAP_FWFWK (writer GEODATABASE_SDE_1)
    PASSED -> AttributeManager_23
    FAILED -> LKMAP_FWPL (writer GEODATABASE_SDE_1)
    FAILED -> AttributeManager_24
LKBE_Standard_linie_4
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_8
Tester_8
    BOOL_OP = OR
    TEST_CLAUSE = TEST @Value(OBJCODE) CONTAINS .Fernwirkkabel
    PASSED -> LKMAP_GASFWK (writer GEODATABASE_SDE_1)
    PASSED -> AttributeManager_25
    FAILED -> LKMAP_GASPL (writer GEODATABASE_SDE_1)
    FAILED -> AttributeManager_26
LKBE_Standard_linie_5
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_7
Tester_7
    BOOL_OP = OR
    TEST_CLAUSE = TEST @Value(OBJCODE) CONTAINS .Fernwirkkabel
    FAILED -> LKMAP_KOMPL (writer GEODATABASE_SDE_1)
    FAILED -> AttributeManager_27
LKBE_Standard_linie_6
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_6
Tester_6
    BOOL_OP = OR
    TEST_CLAUSE = TEST @Value(OBJCODE) CONTAINS .Fernwirkkabel
    PASSED -> LKMAP_WAFWK (writer GEODATABASE_SDE_1)
    PASSED -> AttributeManager_28
    FAILED -> LKMAP_WAPL (writer GEODATABASE_SDE_1)
    FAILED -> AttributeManager_29
LKBE_Standard_linie_7
    BREITE = @Value(breite)
    DATENHERR = @Value(datenherr)
    DATENLIEFERANT = @Value(datenlieferant)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    PROFILTYP = @Value(profiltyp)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_8_Output -> Tester_5
Tester_5
    BOOL_OP = OR
    TEST_CLAUSE = TEST @Value(OBJCODE) CONTAINS .Fernwirkkabel
    PASSED -> LKMAP_WMFWK (writer GEODATABASE_SDE_1)
    PASSED -> AttributeManager_30
    FAILED -> LKMAP_WMPL (writer GEODATABASE_SDE_1)
    FAILED -> AttributeManager_31
STATUST (reader XLSXR_1)
    attributes: STATUSCODE number(2,0), BEZ_DE char(15), BEZ_FR string, Wert_xtf char(15)
    -> Tester
Tester
    BOOL_OP = OR
    TEST_CLAUSE = TEST @Value(STATUSCODE) ATTRIBUTE_HAS_VALUE ""
    PASSED -> LKMAP_STATUST (writer GEODATABASE_SDE_1)
    PASSED -> AttributeManager_2
PROFILT (reader XLSXR_1)
    attributes: PROFILTYP number(2,0), BEZ_DE char(15), BEZ_FR char(14)
    -> Tester_2
Tester_2
    BOOL_OP = OR
    TEST_CLAUSE = TEST @Value(PROFILTYP) ATTRIBUTE_HAS_VALUE ""
    PASSED -> LKMAP_PROFILT (writer GEODATABASE_SDE_1)
    PASSED -> AttributeManager_3
OBJCODET (reader XLSXR_1)
    attributes: OBJCODE char(52), BEZ_DE char(52), BEZ_FR char(78)
    -> Tester_3
Tester_3
    BOOL_OP = OR
    TEST_CLAUSE = TEST @Value(OBJCODE) ATTRIBUTE_HAS_VALUE ""
    PASSED -> LKMAP_OBJCODET (writer GEODATABASE_SDE_1)
    PASSED -> AttributeManager_4
LAGET (reader XLSXR_1)
    attributes: LAGECODE number(2,0), BEZ_DE char(10), BEZ_FR string, Wert_xtf char(10)
    -> Tester_4
Tester_4
    BOOL_OP = OR
    TEST_CLAUSE = TEST @Value(LAGECODE) ATTRIBUTE_HAS_VALUE ""
    PASSED -> LKMAP_LAGET (writer GEODATABASE_SDE_1)
    PASSED -> AttributeManager_5
LKBE_Standard_punkt_2
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_AWPT (writer GEODATABASE_SDE_1)
    AttributeManager_6_Output -> AttributeManager_6
LKBE_Standard_punkt_3
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_EPT (writer GEODATABASE_SDE_1)
    AttributeManager_6_Output -> AttributeManager_7
LKBE_Standard_punkt_4
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_FWPT (writer GEODATABASE_SDE_1)
    AttributeManager_6_Output -> AttributeManager_8
LKBE_Standard_punkt
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_GASPT (writer GEODATABASE_SDE_1)
    AttributeManager_6_Output -> AttributeManager_9
LKBE_Standard_punkt_5
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_KOMPT (writer GEODATABASE_SDE_1)
    AttributeManager_6_Output -> AttributeManager_10
LKBE_Standard_punkt_6
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_WAPT (writer GEODATABASE_SDE_1)
    AttributeManager_6_Output -> AttributeManager_11
LKBE_Standard_punkt_7
    DATENHERR = @Value(datenherr)
    DATENLIEFERANT = @Value(datenlieferant)
    DIMENSION1 = @Value(dimension1)
    DIMENSION2 = @Value(dimension2)
    EIGENTUEMER = @Value(eigentuemer)
    GEOPACKAGE_FID = @Value(geopackage_fid)
    GEOPACKAGE_TYPE = @Value(geopackage_type)
    LAGEBESTIMMUNG = @Value(lagebestimmung)
    LETZTE_AENDERUNG = @Value(letzte_aenderung)
    MULTI_READER_FULL_ID = @Value(multi_reader_full_id)
    MULTI_READER_ID = @Value(multi_reader_id)
    OBJEKTART = @Value(objektart)
    OBJ_ID = @Value(obj_id)
    SIA405_LKMAP_LKFLAECHE_METAATTRIBUTE = @Value(sia405_lkmap_lkflaeche_metaattribute)
    SIA405_LKMAP_LKLINIE_METAATTRIBUTE = @Value(sia405_lkmap_lklinie_metaattribute)
    SIA405_LKMAP_LKPUNKT_METAATTRIBUTE = @Value(sia405_lkmap_lkpunkt_metaattribute)
    STATUS = @Value(status)
    SYMBOLORI = @Value(symbolori)
    T_ID = @Value(T_Id)
    T_ID:1 = @Value(T_Id:1)
    T_ID_NEW = @Value(T_Id_new)
    T_ID_NEW:1 = @Value(T_Id_new:1)
    T_ILI_TID = @Value(T_Ili_Tid)
    T_SEQ = @Value(T_Seq)
    AttributeManager_6_Output -> LKMAP_WMPT (writer GEODATABASE_SDE_1)
    AttributeManager_6_Output -> AttributeManager_12

Bookmark: Geopackage mit Views
v_lkflaeche_meta_abwasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), objektart text(255), eigentuemer text(80), lagebestimmung text(255), status text(255), obj_id text(16), T_Id_new:1 int
    -> LKBE_Standard_flaeche_2 [LKBE_Standard_LAGETValueMapper_Input_1]
v_lkflaeche_meta_elektrizitaet (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), objektart text(255), eigentuemer text(80), lagebestimmung text(255), status text(255), obj_id text(16), T_Id_new:1 int
    -> LKBE_Standard_flaeche_3 [LKBE_Standard_LAGETValueMapper_Input_1]
v_lkflaeche_meta_fernwaerme (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), objektart text(255), eigentuemer text(80), lagebestimmung text(255), status text(255), obj_id text(16), T_Id_new:1 int
    -> LKBE_Standard_flaeche [LKBE_Standard_LAGETValueMapper_Input_1]
v_lkflaeche_meta_gas (reader GEOPACKAGE_1)
    attributes: T_Id int, T_basket int, T_Seq int, datenherr text(80), datenlieferant text(80), letzte_aenderung date, sia405_lkmap_lkflaeche_metaattribute int, sia405_lkmap_lklinie_metaattribute int, sia405_lkmap_lkpunkt_metaattribute int, T_Id_new int, T_Id:1 int, T_basket:1 int, T_Ili_Tid text(200), objektart text(255), eigentuemer text(80), lagebestimmung text(255), status text(255), obj_id text(16), T_Id_new:1 int
    -> LKBE_Standard_flaeche_4 [LKBE_Standard_LAGETValueMapper_Input_1]
v_lkflaeche_meta_kommunikation (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), objektart text(255), eigentuemer text(80), lagebestimmung text(255), status text(255), obj_id text(16), T_Id_new:1 int
    -> LKBE_Standard_flaeche_5 [LKBE_Standard_LAGETValueMapper_Input_1]
v_lkflaeche_meta_wasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), objektart text(255), eigentuemer text(80), lagebestimmung text(255), status text(255), obj_id text(16), T_Id_new:1 int
    -> LKBE_Standard_flaeche_6 [LKBE_Standard_LAGETValueMapper_Input_1]
v_lkflaeche_meta_weiteremedien (reader GEOPACKAGE_1)
    attributes: T_Id int, T_basket int, T_Seq int, datenherr text(80), datenlieferant text(80), letzte_aenderung date, sia405_lkmap_lkflaeche_metaattribute int, sia405_lkmap_lklinie_metaattribute int, sia405_lkmap_lkpunkt_metaattribute int, T_Id_new int, T_Id:1 int, T_basket:1 int, T_Ili_Tid text(200), objektart text(255), eigentuemer text(80), lagebestimmung text(255), status text(255), obj_id text(16), T_Id_new:1 int
    -> LKBE_Standard_flaeche_7 [LKBE_Standard_LAGETValueMapper_Input_1]
v_lklinie_meta_abwasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie [LKBE_Standard_2_LAGETValueMapper_Input]
v_lklinie_meta_elektrizitaet (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie_2 [LKBE_Standard_2_LAGETValueMapper_Input]
v_lklinie_meta_fernwaerme (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie_3 [LKBE_Standard_2_LAGETValueMapper_Input]
v_lklinie_meta_gas (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie_4 [LKBE_Standard_2_LAGETValueMapper_Input]
v_lklinie_meta_kommunikation (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie_5 [LKBE_Standard_2_LAGETValueMapper_Input]
v_lklinie_meta_wasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), breite int, objektart text(255), profiltyp text(255), eigentuemer text(80), lagebestimmung text(255), status text(255), obj_id text(16), T_Id_new:1 int
    -> LKBE_Standard_linie_6 [LKBE_Standard_2_LAGETValueMapper_Input]
v_lklinie_meta_weiteremedien (reader GEOPACKAGE_1)
    attributes: T_Id int, T_basket int, T_Seq int, datenherr text(80), datenlieferant text(80), letzte_aenderung date, sia405_lkmap_lkflaeche_metaattribute int, sia405_lkmap_lklinie_metaattribute int, sia405_lkmap_lkpunkt_metaattribute int, T_Id_new int, T_Id:1 int, T_basket:1 int, T_Ili_Tid text(200), breite int, objektart text(255), profiltyp text(255), eigentuemer text(80), lagebestimmung text(255), status text(255), obj_id text(16), T_Id_new:1 int
    -> LKBE_Standard_linie_7 [LKBE_Standard_2_LAGETValueMapper_Input]
v_lkpunkt_meta_abwasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), dimension1 int, dimension2 int, objektart text(255), symbolori double, eigentuemer text(80), lagebestimmung text(255), status text(255), obj_id text(16), T_Id_new:1 int
    -> LKBE_Standard_punkt_2 [LKBE_Standard_3_LAGETValueMapper_Input]
v_lkpunkt_meta_elektrizitaet (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), dimension1 int, dimension2 int, objektart text(255), symbolori double, eigentuemer text(80), lagebestimmung text(255), status text(255), obj_id text(16), T_Id_new:1 int
    -> LKBE_Standard_punkt_3 [LKBE_Standard_3_LAGETValueMapper_Input]
v_lkpunkt_meta_fernwaerme (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), dimension1 int, dimension2 int, objektart text(255), symbolori double, eigentuemer text(80), lagebestimmung text(255), status text(255), obj_id text(16), T_Id_new:1 int
    -> LKBE_Standard_punkt_4 [LKBE_Standard_3_LAGETValueMapper_Input]
v_lkpunkt_meta_gas (reader GEOPACKAGE_1)
    attributes: T_Id int, T_basket int, T_Seq int, datenherr text(80), datenlieferant text(80), letzte_aenderung date, sia405_lkmap_lkflaeche_metaattribute int, sia405_lkmap_lklinie_metaattribute int, sia405_lkmap_lkpunkt_metaattribute int, T_Id_new int, T_Id:1 int, T_basket:1 int, T_Ili_Tid text(200), dimension1 int, dimension2 int, objektart text(255), symbolori double, eigentuemer text(80), lagebestimmung text(255), status text(255), obj_id text(16), T_Id_new:1 int
    -> LKBE_Standard_punkt [LKBE_Standard_3_LAGETValueMapper_Input]
v_lkpunkt_meta_kommunikation (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), dimension1 int, dimension2 int, objektart text(255), symbolori double, eigentuemer text(80), lagebestimmung text(255), status text(255), obj_id text(16), T_Id_new:1 int
    -> LKBE_Standard_punkt_5 [LKBE_Standard_3_LAGETValueMapper_Input]
v_lkpunkt_meta_wasser (reader GEOPACKAGE_1)
    attributes: T_Id int, T_Seq int, datenherr text(80), datenlieferant text(80), letzte_aenderung date, sia405_lkmap_lkflaeche_metaattribute int, sia405_lkmap_lklinie_metaattribute int, sia405_lkmap_lkpunkt_metaattribute int, T_Id_new int, T_Id:1 int, T_Ili_Tid text(200), dimension1 int, dimension2 int, objektart text(255), symbolori double, eigentuemer text(80), lagebestimmung text(255), status text(255), obj_id text(16), T_Id_new:1 int
    -> LKBE_Standard_punkt_6 [LKBE_Standard_3_LAGETValueMapper_Input]
v_lkpunkt_meta_weiteremedien (reader GEOPACKAGE_1)
    attributes: T_Id int, T_basket int, T_Seq int, datenherr text(80), datenlieferant text(80), letzte_aenderung date, sia405_lkmap_lkflaeche_metaattribute int, sia405_lkmap_lklinie_metaattribute int, sia405_lkmap_lkpunkt_metaattribute int, T_Id_new int, T_Id:1 int, T_basket:1 int, T_Ili_Tid text(200), dimension1 int, dimension2 int, objektart text(255), symbolori double, eigentuemer text(80), lagebestimmung text(255), status text(255), obj_id text(16), T_Id_new:1 int
    -> LKBE_Standard_punkt_7 [LKBE_Standard_3_LAGETValueMapper_Input]

Bookmark: Polygone Norm.sde
LKMAP_AWPG (writer GEODATABASE_SDE_1)
    attributes: EIGENTUMER char(80), LAGECODE smallint, STATUSCODE smallint, OBJCODE char(100), OBJ_ID char(16), DATENHERR char(80), DATENLIEF char(80), AENDERUNG char(10)
LKMAP_EPG (writer GEODATABASE_SDE_1)
    attributes: EIGENTUMER char(80), LAGECODE smallint, STATUSCODE smallint, OBJCODE char(100), OBJ_ID char(16), DATENHERR char(80), DATENLIEF char(80), AENDERUNG char(10)
LKMAP_FWPG (writer GEODATABASE_SDE_1)
    attributes: EIGENTUMER char(80), LAGECODE smallint, STATUSCODE smallint, OBJCODE char(100), OBJ_ID char(16), DATENHERR char(80), DATENLIEF char(80), AENDERUNG char(10)
LKMAP_GASPG (writer GEODATABASE_SDE_1)
    attributes: EIGENTUMER char(80), LAGECODE smallint, STATUSCODE smallint, OBJCODE char(100), OBJ_ID char(16), DATENHERR char(80), DATENLIEF char(80), AENDERUNG char(10)
LKMAP_KOMPG (writer GEODATABASE_SDE_1)
    attributes: EIGENTUMER char(80), LAGECODE smallint, STATUSCODE smallint, OBJCODE char(100), OBJ_ID char(16), DATENHERR char(80), DATENLIEF char(80), AENDERUNG char(10)
LKMAP_WAPG (writer GEODATABASE_SDE_1)
    attributes: EIGENTUMER char(80), LAGECODE smallint, STATUSCODE smallint, OBJCODE char(100), OBJ_ID char(16), DATENHERR char(80), DATENLIEF char(80), AENDERUNG char(10)
LKMAP_WMPG (writer GEODATABASE_SDE_1)
    attributes: EIGENTUMER char(80), LAGECODE smallint, STATUSCODE smallint, OBJCODE char(100), OBJ_ID char(16), DATENHERR char(80), DATENLIEF char(80), AENDERUNG char(10)

Bookmark: PostGIS für Feature Count
AttributeManager_13
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_awpg (writer POSTGIS_1)
AttributeManager_14
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_epg (writer POSTGIS_1)
AttributeManager_15
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_fwpg (writer POSTGIS_1)
AttributeManager_16
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_gaspg (writer POSTGIS_1)
AttributeManager_17
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_kompg (writer POSTGIS_1)
AttributeManager_18
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_wapg (writer POSTGIS_1)
AttributeManager_19
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_wmpg (writer POSTGIS_1)
AttributeManager_20
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_awfwk (writer POSTGIS_1)
AttributeManager_21
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_awpl (writer POSTGIS_1)
AttributeManager_22
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_epl (writer POSTGIS_1)
AttributeManager_23
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_fwfwk (writer POSTGIS_1)
AttributeManager_24
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_fwpl (writer POSTGIS_1)
AttributeManager_25
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_gasfwk (writer POSTGIS_1)
AttributeManager_26
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_gaspl (writer POSTGIS_1)
AttributeManager_27
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_kompl (writer POSTGIS_1)
AttributeManager_28
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_wafwk (writer POSTGIS_1)
AttributeManager_29
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_wapl (writer POSTGIS_1)
AttributeManager_30
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_wmfwk (writer POSTGIS_1)
AttributeManager_31
    ATTR_TABLE:
      RENAME_SET_VALUE LAGECODE > lagecode
      RENAME_SET_VALUE STATUSCODE > statuscode
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
      RENAME_SET_VALUE BREITE > breite
      RENAME_SET_VALUE PROFILTYP > profiltyp
      RENAME_SET_VALUE BREITESYMB > breitesymb
    -> lkmap_wmpl (writer POSTGIS_1)
AttributeManager_2
    ATTR_TABLE:
      RENAME_SET_VALUE STATUSCODE > statuscode
      RENAME_SET_VALUE BEZ_DE > bez_de
      RENAME_SET_VALUE BEZ_FR > bez_fr
    -> lkmap_statust (writer POSTGRES_1)
AttributeManager_3
    ATTR_TABLE:
      RENAME_SET_VALUE BEZ_DE > bez_de
      RENAME_SET_VALUE BEZ_FR > bez_fr
      RENAME_SET_VALUE PROFILTYP > profiltyp
    -> lkmap_profilt (writer POSTGRES_1)
AttributeManager_4
    ATTR_TABLE:
      RENAME_SET_VALUE BEZ_DE > bez_de
      RENAME_SET_VALUE BEZ_FR > bez_fr
      RENAME_SET_VALUE OBJCODE > objcode
    -> lkmap_objcodet (writer POSTGRES_1)
AttributeManager_5
    ATTR_TABLE:
      RENAME_SET_VALUE BEZ_DE > bez_de
      RENAME_SET_VALUE BEZ_FR > bez_fr
      RENAME_SET_VALUE LAGECODE > lagecode
    -> lkmap_laget (writer POSTGRES_1)
AttributeManager_6
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_awpt (writer POSTGIS_1)
AttributeManager_7
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_ept (writer POSTGIS_1)
AttributeManager_8
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_fwpt (writer POSTGIS_1)
AttributeManager_9
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_gaspt (writer POSTGIS_1)
AttributeManager_10
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_kompt (writer POSTGIS_1)
AttributeManager_11
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> lkmap_wapt (writer POSTGIS_1)
AttributeManager_12
    ATTR_TABLE:
      RENAME_SET_VALUE LAGECODE > lagecode
      RENAME_SET_VALUE STATUSCODE > statuscode
      RENAME_SET_VALUE SYMBOLORI > symbolori
      RENAME_SET_VALUE DATENHERR > datenherr
      RENAME_SET_VALUE DATENLIEF > datenlief
      RENAME_SET_VALUE AENDERUNG > aenderung
      RENAME_SET_VALUE OBJCODE > objcode
      RENAME_SET_VALUE EIGENTUMER > eigentumer
      RENAME_SET_VALUE OBJ_ID > obj_id
    -> norm.lkmap_wmpt (writer POSTGIS_1)

Bookmark: Polygone PG
lkmap_awpg (writer POSTGIS_1)
    attributes: objcode varchar(100), statuscode int2, lagecode int2, eigentumer varchar(80), obj_id varchar(16), aenderung varchar(10), datenherr varchar(80), datenlief varchar(80)
lkmap_epg (writer POSTGIS_1)
    attributes: objcode varchar(100), statuscode int2, lagecode int2, eigentumer varchar(80), obj_id varchar(16), aenderung varchar(10), datenherr varchar(80), datenlief varchar(80)
lkmap_fwpg (writer POSTGIS_1)
    attributes: objcode varchar(100), statuscode int2, lagecode int2, eigentumer varchar(80), obj_id varchar(16), aenderung varchar(10), datenherr varchar(80), datenlief varchar(80)
lkmap_gaspg (writer POSTGIS_1)
    attributes: objcode varchar(100), statuscode int2, lagecode int2, eigentumer varchar(80), obj_id varchar(16), aenderung varchar(10), datenherr varchar(80), datenlief varchar(80)
lkmap_kompg (writer POSTGIS_1)
    attributes: objcode varchar(100), statuscode int2, lagecode int2, eigentumer varchar(80), obj_id varchar(16), aenderung varchar(10), datenherr varchar(80), datenlief varchar(80)
lkmap_wapg (writer POSTGIS_1)
    attributes: objcode varchar(100), statuscode int2, lagecode int2, eigentumer varchar(80), obj_id varchar(16), aenderung varchar(10), datenherr varchar(80), datenlief varchar(80)
lkmap_wmpg (writer POSTGIS_1)
    attributes: objcode varchar(100), statuscode int2, lagecode int2, eigentumer varchar(80), obj_id varchar(16), aenderung varchar(10), datenherr varchar(80), datenlief varchar(80)

Bookmark: Polylinien FGDB
LKMAP_AWFWK (writer GEODATABASE_SDE_1)
    attributes: BREITE integer, PROFILTYP smallint, BREITESYMB smallint, EIGENTUMER char(80), LAGECODE smallint, STATUSCODE smallint, OBJCODE char(100), OBJ_ID char(16), DATENHERR char(80), DATENLIEF char(80), AENDERUNG char(10)
LKMAP_AWPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_EPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_FWFWK (writer GEODATABASE_SDE_1)
    attributes: BREITE integer, PROFILTYP smallint, BREITESYMB smallint, EIGENTUMER char(80), LAGECODE smallint, STATUSCODE smallint, OBJCODE char(100), OBJ_ID char(16), DATENHERR char(80), DATENLIEF char(80), AENDERUNG char(10)
LKMAP_FWPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_GASFWK (writer GEODATABASE_SDE_1)
    attributes: BREITE integer, PROFILTYP smallint, BREITESYMB smallint, EIGENTUMER char(80), LAGECODE smallint, STATUSCODE smallint, OBJCODE char(100), OBJ_ID char(16), DATENHERR char(80), DATENLIEF char(80), AENDERUNG char(10)
LKMAP_GASPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_KOMPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_WAFWK (writer GEODATABASE_SDE_1)
    attributes: BREITE integer, PROFILTYP smallint, BREITESYMB smallint, EIGENTUMER char(80), LAGECODE smallint, STATUSCODE smallint, OBJCODE char(100), OBJ_ID char(16), DATENHERR char(80), DATENLIEF char(80), AENDERUNG char(10)
LKMAP_WAPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)
LKMAP_WMFWK (writer GEODATABASE_SDE_1)
    attributes: BREITE integer, PROFILTYP smallint, BREITESYMB smallint, EIGENTUMER char(80), LAGECODE smallint, STATUSCODE smallint, OBJCODE char(100), OBJ_ID char(16), DATENHERR char(80), DATENLIEF char(80), AENDERUNG char(10)
LKMAP_WMPL (writer GEODATABASE_SDE_1)
    attributes: BREITE integer, BREITESYMB smallint, PROFILTYP smallint, EIGENTUMER char(80), LAGECODE smallint, STATUSCODE smallint, OBJCODE char(100), OBJ_ID char(16), DATENHERR char(80), DATENLIEF char(80), AENDERUNG char(10)

Bookmark: Polylinien PG
lkmap_awfwk (writer POSTGIS_1)
    attributes: breite int4, profiltyp int2, breitesymb int2, eigentumer varchar(80), lagecode int2, statuscode int2, objcode varchar(100), obj_id varchar(16), datenherr varchar(80), datenlief varchar(80), aenderung varchar(10)
lkmap_awpl (writer POSTGIS_1)
    attributes: objcode varchar(100), statuscode int2, lagecode int2, eigentumer varchar(80), obj_id varchar(16), breite int4, profiltyp int2, aenderung varchar(10), datenherr varchar(80), datenlief varchar(80), breitesymb int2
lkmap_epl (writer POSTGIS_1)
    attributes: objcode varchar(100), statuscode int2, lagecode int2, eigentumer varchar(80), obj_id varchar(16), breite int4, profiltyp int2, aenderung varchar(10), datenherr varchar(80), datenlief varchar(80), breitesymb int2
lkmap_fwfwk (writer POSTGIS_1)
    attributes: breite int4, profiltyp int2, breitesymb int2, eigentumer varchar(80), lagecode int2, statuscode int2, objcode varchar(100), obj_id varchar(16), datenherr varchar(80), datenlief varchar(80), aenderung varchar(10)
lkmap_fwpl (writer POSTGIS_1)
    attributes: objcode varchar(100), statuscode int2, lagecode int2, eigentumer varchar(80), obj_id varchar(16), breite int4, profiltyp int2, aenderung varchar(10), datenherr varchar(80), datenlief varchar(80), breitesymb int2
lkmap_gasfwk (writer POSTGIS_1)
    attributes: breite int4, profiltyp int2, breitesymb int2, eigentumer varchar(80), lagecode int2, statuscode int2, objcode varchar(100), obj_id varchar(16), datenherr varchar(80), datenlief varchar(80), aenderung varchar(10)
lkmap_gaspl (writer POSTGIS_1)
    attributes: objcode varchar(100), statuscode int2, lagecode int2, eigentumer varchar(80), obj_id varchar(16), breite int4, profiltyp int2, aenderung varchar(10), datenherr varchar(80), datenlief varchar(80), breitesymb int2
lkmap_kompl (writer POSTGIS_1)
    attributes: objcode varchar(100), statuscode int2, lagecode int2, eigentumer varchar(80), obj_id varchar(16), breite int4, profiltyp int2, aenderung varchar(10), datenherr varchar(80), datenlief varchar(80), breitesymb int2
lkmap_wafwk (writer POSTGIS_1)
    attributes: breite int4, profiltyp int2, breitesymb int2, eigentumer varchar(80), lagecode int2, statuscode int2, objcode varchar(100), obj_id varchar(16), datenherr varchar(80), datenlief varchar(80), aenderung varchar(10)
lkmap_wapl (writer POSTGIS_1)
    attributes: objcode varchar(100), statuscode int2, lagecode int2, eigentumer varchar(80), obj_id varchar(16), breite int4, profiltyp int2, aenderung varchar(10), datenherr varchar(80), datenlief varchar(80), breitesymb int2
lkmap_wmfwk (writer POSTGIS_1)
    attributes: breite int4, profiltyp int2, breitesymb int2, eigentumer varchar(80), lagecode int2, statuscode int2, objcode varchar(100), obj_id varchar(16), datenherr varchar(80), datenlief varchar(80), aenderung varchar(10)
lkmap_wmpl (writer POSTGIS_1)
    attributes: objcode varchar(100), statuscode int2, lagecode int2, eigentumer varchar(80), obj_id varchar(16), breite int4, profiltyp int2, aenderung varchar(10), datenherr varchar(80), datenlief varchar(80), breitesymb int2

Bookmark: Tabellen PG
lkmap_statust (writer POSTGRES_1)
    attributes: statuscode int2, bez_de varchar(80), bez_fr varchar(80)
lkmap_profilt (writer POSTGRES_1)
    attributes: profiltyp int2, bez_de varchar(80), bez_fr varchar(80)
lkmap_objcodet (writer POSTGRES_1)
    attributes: objcode varchar(100), bez_de varchar(100), bez_fr varchar(100)
lkmap_laget (writer POSTGRES_1)
    attributes: lagecode int2, bez_de varchar(50), bez_fr varchar(50)

Bookmark: Tabellen Norm.sde
LKMAP_STATUST (writer GEODATABASE_SDE_1)
    attributes: STATUSCODE smallint, BEZ_DE char(80), BEZ_FR char(80)
LKMAP_PROFILT (writer GEODATABASE_SDE_1)
    attributes: PROFILTYP smallint, BEZ_DE char(80), BEZ_FR char(80)
LKMAP_OBJCODET (writer GEODATABASE_SDE_1)
    attributes: OBJCODE char(100), BEZ_DE char(100), BEZ_FR char(100)
LKMAP_LAGET (writer GEODATABASE_SDE_1)
    attributes: LAGECODE smallint, BEZ_DE char(80), BEZ_FR char(80)

Bookmark: Punkte PG
lkmap_awpt (writer POSTGIS_1)
    attributes: objcode varchar(100), statuscode int2, lagecode int2, eigentumer varchar(80), obj_id varchar(16), symbolori int4, aenderung varchar(10), datenherr varchar(80), datenlief varchar(80)
lkmap_ept (writer POSTGIS_1)
    attributes: objcode varchar(100), statuscode int2, lagecode int2, eigentumer varchar(80), obj_id varchar(16), symbolori int4, aenderung varchar(10), datenherr varchar(80), datenlief varchar(80)
lkmap_fwpt (writer POSTGIS_1)
    attributes: objcode varchar(100), statuscode int2, lagecode int2, eigentumer varchar(80), obj_id varchar(16), symbolori int4, aenderung varchar(10), datenherr varchar(80), datenlief varchar(80)
lkmap_gaspt (writer POSTGIS_1)
    attributes: objcode varchar(100), statuscode int2, lagecode int2, eigentumer varchar(80), obj_id varchar(16), symbolori int4, aenderung varchar(10), datenherr varchar(80), datenlief varchar(80)
lkmap_kompt (writer POSTGIS_1)
    attributes: objcode varchar(100), statuscode int2, lagecode int2, eigentumer varchar(80), obj_id varchar(16), symbolori int4, aenderung varchar(10), datenherr varchar(80), datenlief varchar(80)
lkmap_wapt (writer POSTGIS_1)
    attributes: objcode varchar(100), statuscode int2, lagecode int2, eigentumer varchar(80), obj_id varchar(16), symbolori int4, aenderung varchar(10), datenherr varchar(80), datenlief varchar(80)
norm.lkmap_wmpt (writer POSTGIS_1)
    attributes: objcode varchar(100), statuscode int2, lagecode int2, eigentumer varchar(80), obj_id varchar(16), symbolori int4, aenderung varchar(10), datenherr varchar(80), datenlief varchar(80)

Bookmark: Punkte FGDB
LKMAP_AWPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_EPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_FWPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_GASPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_KOMPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_WAPT (writer GEODATABASE_SDE_1)
    attributes: SYMBOLORI integer, EIGENTUMER char(80), LAGECODE smallint, STATUSCODE smallint, OBJCODE char(100), OBJ_ID char(16), DATENHERR char(80), DATENLIEF char(80), AENDERUNG char(10)
LKMAP_WMPT (writer GEODATABASE_SDE_1)
    attributes: SYMBOLORI integer, EIGENTUMER char(80), LAGECODE smallint, STATUSCODE smallint, OBJCODE char(100), OBJ_ID char(16), DATENHERR char(80), DATENLIEF char(80), AENDERUNG char(10)

FME custom transformer LKBE_Standard_flaeche

Parameters:
- SIA405_LKMAP_LKLINIE_METAATTRIBUTE = @Value(sia405_lkmap_lklinie_metaattribute)   # Sia405 Lkmap Lklinie Metaattribute
- MULTI_READER_FULL_ID = @Value(multi_reader_full_id)   # Multi Reader Full Id
- SIA405_LKMAP_LKPUNKT_METAATTRIBUTE = @Value(sia405_lkmap_lkpunkt_metaattribute)   # Sia405 Lkmap Lkpunkt Metaattribute
- T_ID_NEW = @Value(T_Id_new)   # T Id New
- OBJEKTART = @Value(objektart)   # objektart
- EIGENTUEMER = @Value(eigentuemer)   # eigentuemer
- SIA405_LKMAP_LKFLAECHE_METAATTRIBUTE = @Value(sia405_lkmap_lkflaeche_metaattribute)   # Sia405 Lkmap Lkflaeche Metaattribute
- T_ID_NEW:1 = @Value(T_Id_new:1)   # T Id New:1
- LETZTE_AENDERUNG = @Value(letzte_aenderung)   # Letzte Aenderung
- GEOPACKAGE_FID = @Value(geopackage_fid)   # Geopackage Fid
- GEOPACKAGE_TYPE = @Value(geopackage_type)   # Geopackage Type
- DATENLIEFERANT = @Value(datenlieferant)   # datenlieferant
- LAGEBESTIMMUNG = @Value(lagebestimmung)   # lagebestimmung
- STATUS = @Value(status)   # status
- MULTI_READER_ID = @Value(multi_reader_id)   # Multi Reader Id
- OBJ_ID = @Value(obj_id)   # Obj Id
- T_SEQ = @Value(T_Seq)   # T Seq
- DATENHERR = @Value(datenherr)   # datenherr
- T_ILI_TID = @Value(T_Ili_Tid)   # T Ili Tid
- T_ID = @Value(T_Id)   # T Id
- T_ID:1 = @Value(T_Id:1)   # T Id:1

LKBE_Standard_LAGETValueMapper_Input_1 (input)
    -> GeometryValidator
GeometryValidator
    ISSUE_ATTR_NAME = _issues
    PRESETS = Custom
    REPAIR = Yes
    RULES = NAN_REMOVAL PROCESS_MEASURE]NO]FME_CONTROLLER_QUERY_FILE]transformers\dependencies\geometryvalidator\NAN_REMOVAL.fme CONSECUTIVE_IDENTICAL_VERTICES_2D CHECK_Z]NO]FME_CONTROLLER_QUERY_FILE]transformers\dependencies\geometryvalidator\CONSECUTIVE_IDENTICAL_VERTICES_2D.fme SELF_INTERSECTING CHECK_HOLE_TOUCHING_POLYGON]No]CONNECT_Z_MODE_SI]FIRST_WINS]FME_CONTROLLER_QUERY_FILE]transformers\dependencies\geometryvalidator\SELF_INTERSECTING.fme TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme
    SUMMARY = Detailed
    PASSED -> LAGETValueMapper
    FAILED -> GeometryValidator_Failed
    REPAIRED -> LAGETValueMapper [off]
    REPAIRED -> GeometryValidator_Repaired
LAGETValueMapper: AttributeValueMapper
    DIRECTION = Forward (Source To Destination)
    LUT = genau,1,unbekannt,2,ungenau,3,FME_NULL_VALUE,0
    SRC = lagebestimmung
    VAL_ATTR = LAGECODE
    -> STATUSValueMapper
STATUSValueMapper: AttributeValueMapper
    DIRECTION = Forward (Source To Destination)
    LUT = ausser_Betrieb,1,in_Betrieb,2,tot,3,unbekannt,4,weitere,5,FME_NULL_VALUE,0
    SRC = status
    VAL_ATTR = STATUSCODE
    -> AttributeManager_2
AttributeManager_2
    ATTR_TABLE:
      REMOVE T_Id_new
      REMOVE T_Id
      REMOVE sia405_lkmap_lkflaeche_metaattribute
      REMOVE sia405_lkmap_lklinie_metaattribute
      REMOVE sia405_lkmap_lkpunkt_metaattribute
      REMOVE T_Seq
      RENAME_SET_VALUE datenherr > DATENHERR
      RENAME_SET_VALUE datenlieferant > DATENLIEF
      RENAME_SET_VALUE letzte_aenderung > AENDERUNG
      REMOVE T_Id:1
      REMOVE T_Ili_Tid
      RENAME_SET_VALUE objektart > OBJCODE
      RENAME_SET_VALUE eigentuemer > EIGENTUMER
      REMOVE lagebestimmung
      REMOVE status
      RENAME_SET_VALUE obj_id > OBJ_ID
      REMOVE T_Id_new:1
      REMOVE geopackage_fid
      REMOVE geopackage_type
      REMOVE multi_reader_full_id
      REMOVE multi_reader_id
    -> DonutHoleExtractor
DonutHoleExtractor
    DEAGGREGATE_INPUT = Yes
    OUTERSHELL -> AttributeManager_2_Output (output)
    HOLE -> AttributeManager_2_Output (output)
AttributeManager_2_Output (output)
GeometryValidator_Failed: Inspector
GeometryValidator_Repaired: Inspector

FME custom transformer LKBE_Standard_punkt

Parameters:
- SIA405_LKMAP_LKLINIE_METAATTRIBUTE = @Value(sia405_lkmap_lklinie_metaattribute)   # Sia405 Lkmap Lklinie Metaattribute
- MULTI_READER_FULL_ID = @Value(multi_reader_full_id)   # Multi Reader Full Id
- DIMENSION2 = @Value(dimension2)   # dimension2
- SIA405_LKMAP_LKPUNKT_METAATTRIBUTE = @Value(sia405_lkmap_lkpunkt_metaattribute)   # Sia405 Lkmap Lkpunkt Metaattribute
- T_ID_NEW = @Value(T_Id_new)   # T Id New
- OBJEKTART = @Value(objektart)   # objektart
- DIMENSION1 = @Value(dimension1)   # dimension1
- EIGENTUEMER = @Value(eigentuemer)   # eigentuemer
- SIA405_LKMAP_LKFLAECHE_METAATTRIBUTE = @Value(sia405_lkmap_lkflaeche_metaattribute)   # Sia405 Lkmap Lkflaeche Metaattribute
- LETZTE_AENDERUNG = @Value(letzte_aenderung)   # Letzte Aenderung
- T_ID_NEW:1 = @Value(T_Id_new:1)   # T Id New:1
- GEOPACKAGE_FID = @Value(geopackage_fid)   # Geopackage Fid
- GEOPACKAGE_TYPE = @Value(geopackage_type)   # Geopackage Type
- DATENLIEFERANT = @Value(datenlieferant)   # datenlieferant
- LAGEBESTIMMUNG = @Value(lagebestimmung)   # lagebestimmung
- STATUS = @Value(status)   # status
- MULTI_READER_ID = @Value(multi_reader_id)   # Multi Reader Id
- OBJ_ID = @Value(obj_id)   # Obj Id
- SYMBOLORI = @Value(symbolori)   # symbolori
- T_SEQ = @Value(T_Seq)   # T Seq
- DATENHERR = @Value(datenherr)   # datenherr
- T_ILI_TID = @Value(T_Ili_Tid)   # T Ili Tid
- T_ID = @Value(T_Id)   # T Id
- T_ID:1 = @Value(T_Id:1)   # T Id:1

LKBE_Standard_3_LAGETValueMapper_Input (input)
    -> LAGETValueMapper
LAGETValueMapper: AttributeValueMapper
    DIRECTION = Forward (Source To Destination)
    LUT = genau,1,unbekannt,2,ungenau,3,FME_NULL_VALUE,0
    SRC = lagebestimmung
    VAL_ATTR = LAGECODE
    -> STATUSValueMapper
STATUSValueMapper: AttributeValueMapper
    DIRECTION = Forward (Source To Destination)
    LUT = ausser_Betrieb,1,in_Betrieb,2,tot,3,unbekannt,4,weitere,5,FME_NULL_VALUE,0
    SRC = status
    VAL_ATTR = STATUSCODE
    -> AttributeManager_6
AttributeManager_6
    ATTR_TABLE:
      REMOVE dimension1
      REMOVE dimension2
      RENAME_SET_VALUE symbolori > SYMBOLORI
      REMOVE T_Id_new
      REMOVE T_Id
      REMOVE sia405_lkmap_lkflaeche_metaattribute
      REMOVE sia405_lkmap_lklinie_metaattribute
      REMOVE sia405_lkmap_lkpunkt_metaattribute
      REMOVE T_Seq
      RENAME_SET_VALUE datenherr > DATENHERR
      RENAME_SET_VALUE datenlieferant > DATENLIEF
      RENAME_SET_VALUE letzte_aenderung > AENDERUNG
      REMOVE T_Id:1
      REMOVE T_Ili_Tid
      RENAME_SET_VALUE objektart > OBJCODE
      RENAME_SET_VALUE eigentuemer > EIGENTUMER
      REMOVE lagebestimmung
      REMOVE status
      RENAME_SET_VALUE obj_id > OBJ_ID
      REMOVE T_Id_new:1
      REMOVE geopackage_fid
      REMOVE geopackage_type
      REMOVE multi_reader_full_id
      REMOVE multi_reader_id
    -> AttributeManager_6_Output (output)
AttributeManager_6_Output (output)

FME custom transformer LKBE_Standard_linie

Parameters:
- SIA405_LKMAP_LKLINIE_METAATTRIBUTE = @Value(sia405_lkmap_lklinie_metaattribute)   # Sia405 Lkmap Lklinie Metaattribute
- MULTI_READER_FULL_ID = @Value(multi_reader_full_id)   # Multi Reader Full Id
- SIA405_LKMAP_LKPUNKT_METAATTRIBUTE = @Value(sia405_lkmap_lkpunkt_metaattribute)   # Sia405 Lkmap Lkpunkt Metaattribute
- T_ID_NEW = @Value(T_Id_new)   # T Id New
- OBJEKTART = @Value(objektart)   # objektart
- BREITE = @Value(breite)   # breite
- EIGENTUEMER = @Value(eigentuemer)   # eigentuemer
- SIA405_LKMAP_LKFLAECHE_METAATTRIBUTE = @Value(sia405_lkmap_lkflaeche_metaattribute)   # Sia405 Lkmap Lkflaeche Metaattribute
- PROFILTYP = @Value(profiltyp)   # profiltyp
- LETZTE_AENDERUNG = @Value(letzte_aenderung)   # Letzte Aenderung
- T_ID_NEW:1 = @Value(T_Id_new:1)   # T Id New:1
- GEOPACKAGE_FID = @Value(geopackage_fid)   # Geopackage Fid
- GEOPACKAGE_TYPE = @Value(geopackage_type)   # Geopackage Type
- DATENLIEFERANT = @Value(datenlieferant)   # datenlieferant
- LAGEBESTIMMUNG = @Value(lagebestimmung)   # lagebestimmung
- STATUS = @Value(status)   # status
- MULTI_READER_ID = @Value(multi_reader_id)   # Multi Reader Id
- OBJ_ID = @Value(obj_id)   # Obj Id
- T_SEQ = @Value(T_Seq)   # T Seq
- DATENHERR = @Value(datenherr)   # datenherr
- T_ILI_TID = @Value(T_Ili_Tid)   # T Ili Tid
- T_ID = @Value(T_Id)   # T Id
- T_ID:1 = @Value(T_Id:1)   # T Id:1

LKBE_Standard_2_LAGETValueMapper_Input (input)
    -> GeometryValidator
GeometryValidator
    ISSUE_ATTR_NAME = _issues
    PRESETS = Custom
    REPAIR = Yes
    RULES = NAN_REMOVAL PROCESS_MEASURE]NO]FME_CONTROLLER_QUERY_FILE]transformers\dependencies\geometryvalidator\NAN_REMOVAL.fme CONSECUTIVE_IDENTICAL_VERTICES_2D CHECK_Z]NO]FME_CONTROLLER_QUERY_FILE]transformers\dependencies\geometryvalidator\CONSECUTIVE_IDENTICAL_VERTICES_2D.fme
    SUMMARY = Detailed
    PASSED -> LAGETValueMapper
    FAILED -> GeometryValidator_Failed
    REPAIRED -> VertexCounter
    REPAIRED -> GeometryValidator_Repaired
LAGETValueMapper: AttributeValueMapper
    DIRECTION = Forward (Source To Destination)
    LUT = genau,1,unbekannt,2,ungenau,3,FME_NULL_VALUE,0
    SRC = lagebestimmung
    VAL_ATTR = LAGECODE
    -> STATUSValueMapper
STATUSValueMapper: AttributeValueMapper
    DIRECTION = Forward (Source To Destination)
    LUT = ausser_Betrieb,1,in_Betrieb,2,tot,3,unbekannt,4,weitere,5,FME_NULL_VALUE,0
    SRC = status
    VAL_ATTR = STATUSCODE
    -> PROFILTYPalueMapper
PROFILTYPalueMapper: AttributeValueMapper
    DIRECTION = Forward (Source To Destination)
    LUT = Eiprofil,1,Kreisprofil,2,Rechteckprofil,3,unbekannt,4,weitere,5,FME_NULL_VALUE,0
    SRC = profiltyp
    VAL_ATTR = PROFILTYP
    -> AttributeManager_8
AttributeManager_8
    ATTR_TABLE:
      REMOVE T_Id_new
      REMOVE T_Id
      REMOVE sia405_lkmap_lkflaeche_metaattribute
      REMOVE sia405_lkmap_lklinie_metaattribute
      REMOVE sia405_lkmap_lkpunkt_metaattribute
      REMOVE T_Seq
      RENAME_SET_VALUE datenherr > DATENHERR
      RENAME_SET_VALUE datenlieferant > DATENLIEF
      RENAME_SET_VALUE letzte_aenderung > AENDERUNG
      REMOVE T_Id:1
      REMOVE T_Ili_Tid
      RENAME_SET_VALUE breite > BREITE
      RENAME_SET_VALUE objektart > OBJCODE
      REMOVE profiltyp
      RENAME_SET_VALUE eigentuemer > EIGENTUMER
      REMOVE lagebestimmung
      REMOVE status
      RENAME_SET_VALUE obj_id > OBJ_ID
      REMOVE T_Id_new:1
      REMOVE geopackage_fid
      REMOVE geopackage_type
      REMOVE multi_reader_full_id
      REMOVE multi_reader_id
    -> AttributeManager
AttributeManager
    ATTR_TABLE = SET_TO BREITESYMB = FME_CONDITIONAL:DEFAULT_VALUE'FME_NULL_VALUE'BOOL_OP;OR;COMPOSITE_TEST;<Unused>;TEST @Value(OBJCODE) CONTAINS .Schutzrohr'3'BOOL_OP;OR;COMPOSITE_TEST;<Unused>;TEST @Value(BREITE) >= 600'2'BOOL_OP;OR;COMPOSITE_TEST;<Unused>;TEST @Value(BREITE) < 600'1'FME_NUM_CONDITIONS4___
    -> AttributeManager_8_Output (output)
AttributeManager_8_Output (output)
GeometryValidator_Failed: Inspector
GeometryValidator_Repaired: Inspector

Bookmark: Remove Points
VertexCounter
    CNT_ATTR = _coordcount
    -> Tester
Tester
    BOOL_OP = OR
    TEST_CLAUSE = TEST @Value(_coordcount) > 1
    PASSED -> LAGETValueMapper
