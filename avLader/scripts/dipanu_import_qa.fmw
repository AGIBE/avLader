FME workspace dipanu_import_qa.fmw

Parameters:
- QA_EXCEL =   # Destination Microsoft Excel File
- NORM_DATABASE =
- NORM_USERNAME =
- NORM_PASSWORD =
- VEK1_DATABASE =
- VEK1_USERNAME =
- VEK1_PASSWORD =
- LOGFILE =

Writers:
- XLSXW_1: XLSXW to $(QA_EXCEL)

Note: VEK1P
SQLCreator
    DATASET = $(VEK1_DATABASE)
    EXPOSED_ATTRIBUTE_LIST = BFSNR,GBKR,ANZAHL,PROJSTAT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select t.bfsnr, t.gbkr, t.projstat, count(*) anzahl from geodb.dipanu_dipanuf t group by t.bfsnr, t.gbkr, t.projstat order by t.bfsnr asc, t.gbkr asc
    RESULT -> BulkAttributeRenamer
BulkAttributeRenamer
    ATTRCHOICE = Selected Attributes
    ATTRLIST = ANZAHL
    MODE_CHOICE = RENAME
    PATTERN_ACTION_DISP = ADDSUFFIX
    REPLACE_STR = _ALT
    -> Tester_2
Tester_2
    BOOL_OP = OR
    TEST_CLAUSE:
      TEST @Value(PROJSTAT) = 0
      TEST @Value(PROJSTAT) = 2
    PASSED -> AttributeValueMapper
    FAILED -> FeatureMerger_3 [REQUESTOR]
AttributeValueMapper
    DIRECTION = Forward (Source To Destination)
    LUT = ,0
    SRC = PROJSTAT
    VAL_ATTR = _looked_up
    -> Aggregator
Aggregator
    ACCUM_ATTRS_NAME = Drop Incoming Attributes
    GROUP_BY = BFSNR GBKR
    MODE = Attributes Only
    ORDERED = No
    SEP = ,
    SUM = ANZAHL_ALT
    AGGREGATE -> FeatureMerger [REQUESTOR]
Note: TEAMP
SQLCreator_2
    DATASET = $(NORM_DATABASE)
    EXPOSED_ATTRIBUTE_LIST = BFSNR,GBKR,ANZAHL,PROJSTAT
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select t.bfsnr, t.gbkr, t.projstat, count(*) anzahl from dipanu_dipanuf t group by t.bfsnr, t.gbkr, t.projstat order by t.bfsnr asc, t.gbkr asc
    RESULT -> BulkAttributeRenamer_2
BulkAttributeRenamer_2
    ATTRCHOICE = Selected Attributes
    ATTRLIST = ANZAHL
    MODE_CHOICE = RENAME
    PATTERN_ACTION_DISP = ADDSUFFIX
    REPLACE_STR = _NEU
    -> Tester_3
Tester_3
    BOOL_OP = OR
    TEST_CLAUSE:
      TEST @Value(PROJSTAT) = 0
      TEST @Value(PROJSTAT) = 2
    PASSED -> AttributeValueMapper_2
    FAILED -> FeatureMerger_3 [SUPPLIER]
FeatureMerger_3
    ATTR_ACCUM_MODE = Merge Supplier
    ATTR_CONFLICT_RES = Use Requestor
    IGNORE_NULLS = No
    JOIN_KEYS = @Value(BFSNR) @Value(BFSNR) AUTO @Value(GBKR) @Value(GBKR) AUTO
    MERGE_TYPE = Attributes Only
    PROCESS_DUPS = NO
    REJECT_NULL_MISSING_KEYS = No
    SUPPLIERS_FIRST = No
    MERGED -> ExpressionEvaluator_5
    UNMERGED_REQUESTOR -> AttributeManager
    UNUSED_SUPPLIER -> AttributeManager_2
AttributeManager
    ATTR_TABLE = SET_TO ANZAHL_NEU = 0
    -> ExpressionEvaluator_5
AttributeManager_2
    ATTR_TABLE = SET_TO ANZAHL_ALT = 0
    -> ExpressionEvaluator_5
ExpressionEvaluator_5
    ACTION = Create New Attribute
    EXPRESSION = (@Value(ANZAHL_NEU)-@Value(ANZAHL_ALT))
    VAL_ATTR = DIFF_ABS
    -> ExpressionEvaluator_6
ExpressionEvaluator_6
    ACTION = Create New Attribute
    EXPRESSION = (@Value(DIFF_ABS)/(@Value(ANZAHL_ALT)/100.0))
    VAL_ATTR = DIFF_REL
    -> Sorter_3
Sorter_3
    SORT_PARM = DIFF_ABS NUMERIC ASCENDING
    SORTED -> unveraendertFlächen_PROJ (writer XLSXW_1)
unveraendertFlächen_PROJ (writer XLSXW_1)
    attributes: BFSNR number(20), GBKR number(20), ANZAHL_ALT number(20), ANZAHL_NEU number(20), DIFF_ABS number(20), DIFF_REL number(30)
AttributeValueMapper_2
    DIRECTION = Forward (Source To Destination)
    LUT = ,0
    SRC = PROJSTAT
    VAL_ATTR = _looked_up
    -> Aggregator_2
Aggregator_2
    ACCUM_ATTRS_NAME = Drop Incoming Attributes
    GROUP_BY = BFSNR GBKR
    MODE = Attributes Only
    ORDERED = No
    SEP = ,
    SUM = ANZAHL_NEU
    AGGREGATE -> FeatureMerger [SUPPLIER]
FeatureMerger
    ATTR_ACCUM_MODE = Merge Supplier
    ATTR_CONFLICT_RES = Use Requestor
    IGNORE_NULLS = No
    JOIN_KEYS = @Value(BFSNR) @Value(BFSNR) AUTO @Value(GBKR) @Value(GBKR) AUTO
    MERGE_TYPE = Attributes Only
    PROCESS_DUPS = NO
    REJECT_NULL_MISSING_KEYS = No
    SUPPLIERS_FIRST = No
    MERGED -> ExpressionEvaluator
    UNMERGED_REQUESTOR -> verschwundenFlächen (writer XLSXW_1)
    UNUSED_SUPPLIER -> hinzugekommenFlächen (writer XLSXW_1)
ExpressionEvaluator
    ACTION = Create New Attribute
    EXPRESSION = (@Value(ANZAHL_NEU)-@Value(ANZAHL_ALT))
    VAL_ATTR = DIFF_ABS
    -> ExpressionEvaluator_2
ExpressionEvaluator_2
    ACTION = Create New Attribute
    EXPRESSION = (@Value(DIFF_ABS)/(@Value(ANZAHL_ALT)/100.0))
    VAL_ATTR = DIFF_REL
    -> Sorter
Sorter
    SORT_PARM = DIFF_ABS NUMERIC ASCENDING
    SORTED -> unveraendertFlächen (writer XLSXW_1)
unveraendertFlächen (writer XLSXW_1)
    attributes: BFSNR number(20), GBKR number(20), ANZAHL_ALT number(20), ANZAHL_NEU number(20), DIFF_ABS number(20), DIFF_REL number(30)
verschwundenFlächen (writer XLSXW_1)
    attributes: BFSNR number(20), GBKR number(20), ANZAHL number(20)
hinzugekommenFlächen (writer XLSXW_1)
    attributes: BFSNR number(20), GBKR number(20), ANZAHL number(20)
Note: VEK1P
SQLCreator_9
    DATASET = $(VEK1_DATABASE)
    EXPOSED_ATTRIBUTE_LIST = BFSNR,GBKR,ANZAHL,PROJSTAT
    FORMAT = ORACLE8I_DB
    ORACLE8I_DB_PASSWORD = $(VEK1_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(VEK1_USERNAME)
    ORACLE8I_DB_USE_UNIFIED_DATE_ATTRS = YES
    SQL_STATEMENT = select t.bfsnr, t.gbkr, t.projstat, count(*) anzahl from geodb.dipanu_dipanup t group by t.bfsnr, t.gbkr, t.projstat order by t.bfsnr asc, t.gbkr asc
    RESULT -> BulkAttributeRenamer_4
BulkAttributeRenamer_4
    ATTRCHOICE = Selected Attributes
    ATTRLIST = ANZAHL
    MODE_CHOICE = RENAME
    PATTERN_ACTION_DISP = ADDSUFFIX
    REPLACE_STR = _ALT
    -> Tester_4
Tester_4
    BOOL_OP = OR
    TEST_CLAUSE:
      TEST @Value(PROJSTAT) = 0
      TEST @Value(PROJSTAT) = 2
    PASSED -> AttributeValueMapper_3
    FAILED -> FeatureMerger_4 [REQUESTOR]
AttributeValueMapper_3
    DIRECTION = Forward (Source To Destination)
    LUT = ,0
    SRC = PROJSTAT
    VAL_ATTR = _looked_up
    -> Aggregator_3
Aggregator_3
    ACCUM_ATTRS_NAME = Drop Incoming Attributes
    GROUP_BY = BFSNR GBKR
    MODE = Attributes Only
    ORDERED = No
    SEP = ,
    SUM = ANZAHL_ALT
    AGGREGATE -> FeatureMerger_2 [REQUESTOR]
Note: TEAMP
SQLCreator_10
    DATASET = $(NORM_DATABASE)
    EXPOSED_ATTRIBUTE_LIST = BFSNR,GBKR,ANZAHL,PROJSTAT
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT = select t.bfsnr, t.gbkr, t.projstat, count(*) anzahl from dipanu_dipanup t group by t.bfsnr, t.gbkr, t.projstat order by t.bfsnr asc, t.gbkr asc
    RESULT -> BulkAttributeRenamer_3
BulkAttributeRenamer_3
    ATTRCHOICE = Selected Attributes
    ATTRLIST = ANZAHL
    MODE_CHOICE = RENAME
    PATTERN_ACTION_DISP = ADDSUFFIX
    REPLACE_STR = _NEU
    -> Tester_5
Tester_5
    BOOL_OP = OR
    TEST_CLAUSE:
      TEST @Value(PROJSTAT) = 0
      TEST @Value(PROJSTAT) = 2
    PASSED -> AttributeValueMapper_4
    FAILED -> FeatureMerger_4 [SUPPLIER]
AttributeValueMapper_4
    DIRECTION = Forward (Source To Destination)
    LUT = ,0
    SRC = PROJSTAT
    VAL_ATTR = _looked_up
    -> Aggregator_4
Aggregator_4
    ACCUM_ATTRS_NAME = Drop Incoming Attributes
    GROUP_BY = BFSNR GBKR
    MODE = Attributes Only
    ORDERED = No
    SEP = ,
    SUM = ANZAHL_NEU
    AGGREGATE -> FeatureMerger_2 [SUPPLIER]
FeatureMerger_2
    ATTR_ACCUM_MODE = Merge Supplier
    ATTR_CONFLICT_RES = Use Requestor
    IGNORE_NULLS = No
    JOIN_KEYS = @Value(BFSNR) @Value(BFSNR) AUTO @Value(GBKR) @Value(GBKR) AUTO
    MERGE_TYPE = Attributes Only
    PROCESS_DUPS = NO
    REJECT_NULL_MISSING_KEYS = No
    SUPPLIERS_FIRST = No
    MERGED -> ExpressionEvaluator_3
    UNMERGED_REQUESTOR -> verschwundenPoint (writer XLSXW_1)
    UNUSED_SUPPLIER -> hinzugekommenPoint (writer XLSXW_1)
ExpressionEvaluator_3
    ACTION = Create New Attribute
    EXPRESSION = (@Value(ANZAHL_NEU)-@Value(ANZAHL_ALT))
    VAL_ATTR = DIFF_ABS
    -> ExpressionEvaluator_4
ExpressionEvaluator_4
    ACTION = Create New Attribute
    EXPRESSION = (@Value(DIFF_ABS)/(@Value(ANZAHL_ALT)/100.0))
    VAL_ATTR = DIFF_REL
    -> Sorter_2
Sorter_2
    SORT_PARM = DIFF_ABS NUMERIC ASCENDING
    SORTED -> unveraendertPunkte (writer XLSXW_1)
unveraendertPunkte (writer XLSXW_1)
    attributes: BFSNR number(20), GBKR number(20), ANZAHL_ALT number(20), ANZAHL_NEU number(20), DIFF_ABS number(20), DIFF_REL number(30)
verschwundenPoint (writer XLSXW_1)
    attributes: BFSNR number(20), GBKR number(20), ANZAHL number(20)
hinzugekommenPoint (writer XLSXW_1)
    attributes: BFSNR number(20), GBKR number(20), ANZAHL number(20)
FeatureMerger_4
    ATTR_ACCUM_MODE = Merge Supplier
    ATTR_CONFLICT_RES = Use Requestor
    IGNORE_NULLS = No
    JOIN_KEYS = @Value(BFSNR) @Value(BFSNR) AUTO @Value(GBKR) @Value(GBKR) AUTO
    MERGE_TYPE = Attributes Only
    PROCESS_DUPS = NO
    REJECT_NULL_MISSING_KEYS = No
    SUPPLIERS_FIRST = No
    MERGED -> ExpressionEvaluator_7
    UNMERGED_REQUESTOR -> AttributeManager_3
    UNUSED_SUPPLIER -> AttributeManager_4
AttributeManager_3
    ATTR_TABLE = SET_TO ANZAHL_NEU = 0
    -> ExpressionEvaluator_7
AttributeManager_4
    ATTR_TABLE = SET_TO ANZAHL_ALT = 0
    -> ExpressionEvaluator_7
ExpressionEvaluator_7
    ACTION = Create New Attribute
    EXPRESSION = (@Value(ANZAHL_NEU)-@Value(ANZAHL_ALT))
    VAL_ATTR = DIFF_ABS
    -> ExpressionEvaluator_8
ExpressionEvaluator_8
    ACTION = Create New Attribute
    EXPRESSION = (@Value(DIFF_ABS)/(@Value(ANZAHL_ALT)/100.0))
    VAL_ATTR = DIFF_REL
    -> Sorter_4
Sorter_4
    SORT_PARM = DIFF_ABS NUMERIC ASCENDING
    SORTED -> unveraendertPunkte_PROJ (writer XLSXW_1)
unveraendertPunkte_PROJ (writer XLSXW_1)
    attributes: BFSNR number(20), GBKR number(20), ANZAHL_ALT number(20), ANZAHL_NEU number(20), DIFF_ABS number(20), DIFF_REL number(30)
SQLCreator_4
    DATASET = $(NORM_DATABASE)
    EXPOSED_ATTRIBUTE_LIST = BFSNR,GEMNAME,GBKR,GSTBEZ,PROJSTAT,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.bfsnr, t.gbkr, t.gstbez, t.projstat, count(*) anzahl
        from dipanu_dipanuf t
       group by t.bfsnr, t.gbkr, t.gstbez, t.projstat
       having count(*) > 1
       order by t.bfsnr asc, t.gbkr asc, t.gstbez asc, t.projstat asc
    RESULT -> doppelte2_Flächen (writer XLSXW_1)
doppelte2_Flächen (writer XLSXW_1)
    attributes: BFSNR number(20), GBKR number(20), GSTBEZ string(30), ANZAHL number(20), PROJSTAT number(20)
SQLCreator_5
    DATASET = $(NORM_DATABASE)
    EXPOSED_ATTRIBUTE_LIST = GENGBKRI,GSTBEZ,PROJSTAT
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.gengbkri, t.gstbez, t.projstat, count(*) anzahl
        from dipanu_dipanuf t
       group by t.gengbkri, t.gstbez, t.projstat
       having count(*) > 1
       order by t.gengbkri, t.gstbez, t.projstat
    RESULT -> doppelte3_Flächen (writer XLSXW_1)
doppelte3_Flächen (writer XLSXW_1)
    attributes: GENGBKRI number(20), GSTBEZ string(50), PROJSTAT number(20)
SQLCreator_11
    DATASET = $(NORM_DATABASE)
    EXPOSED_ATTRIBUTE_LIST = EGRID,PROJSTAT,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.egrid, t.projstat, count(*) anzahl
        from dipanu_dipanuf t
       group by t.egrid, t.projstat
       having count(*) > 1
       order by t.egrid asc, t.projstat asc
    RESULT -> doppelte_EGRID (writer XLSXW_1)
doppelte_EGRID (writer XLSXW_1)
    attributes: EGRID string(50), PROJSTAT number(20), ANZAHL number(20)
SQLCreator_6
    DATASET = $(NORM_DATABASE)
    EXPOSED_ATTRIBUTE_LIST = BFSNR,GEMNAME,GBKR,GSTBEZ,PROJSTAT,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.bfsnr, t.gbkr, t.gstbez, t.projstat, count(*) anzahl
        from dipanu_dipanup t
       group by t.bfsnr, t.gbkr, t.gstbez, t.projstat
       having count(*) > 1
       order by t.bfsnr asc, t.gbkr asc, t.gstbez asc, t.projstat asc
    RESULT -> doppelte_Punkte (writer XLSXW_1)
doppelte_Punkte (writer XLSXW_1)
    attributes: BFSNR number(20), GBKR number(20), GSTBEZ string(30), PROJSTAT number(20), ANZAHL number(20)
SQLCreator_7
    DATASET = $(NORM_DATABASE)
    EXPOSED_ATTRIBUTE_LIST = BFSNR,GEMNAME,GBKR,GSTNR,GZNR,GSTTEIL,GSTART,PROJSTAT,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.bfsnr, t.gbkr, t.gstnr, t.gznr, t.gstteil, t.gstart, t.projstat, count(*) anzahl
        from dipanu_dipanup t
       group by t.bfsnr, t.gbkr, t.gstnr, t.gznr, t.gstteil, t.gstart, t.projstat
       having count(*) > 1
       order by t.bfsnr asc, t.gbkr asc, t.gstnr asc, t.gznr asc, t.gstteil asc, t.gstart asc, t.projstat asc
    RESULT -> doppelte2_Punkte (writer XLSXW_1)
doppelte2_Punkte (writer XLSXW_1)
    attributes: BFSNR number(20), GBKR number(20), ANZAHL number(20), GEMNAME string(50), GSTNR number(20), GSTTEIL number(20), GSTART number(20), GZNR string(20), PROJSTAT number(20)
SQLCreator_8
    DATASET = $(NORM_DATABASE)
    EXPOSED_ATTRIBUTE_LIST = GENGBKRI,GSTBEZ,PROJSTAT
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.gengbkri, t.gstbez, t.projstat, count(*) anzahl
        from dipanu_dipanup t
       group by t.gengbkri, t.gstbez, t.projstat
       having count(*) > 1
       order by t.gengbkri, t.gstbez, t.projstat
    RESULT -> doppelte3_Punkte (writer XLSXW_1)
doppelte3_Punkte (writer XLSXW_1)
    attributes: GENGBKRI number(20), GSTBEZ string(50), PROJSTAT number(20)
