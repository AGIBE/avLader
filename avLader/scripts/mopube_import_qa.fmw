FME workspace mopube_import_qa.fmw

Parameters:
- NORM_DATABASE =   # Norm-DB
- NORM_USERNAME =   # Norm-Username
- NORM_PASSWORD =   # Norm-Password
- VEK1_DATABASE =   # Vek1-Database
- VEK1_USERNAME =   # Vek1-Username
- VEK1_PASSWORD =   # Vek1-Passwort
- LOGFILE =   # Logfile
- QA_EXCEL =   # Destination Microsoft Excel File

Writers:
- XLSXW_1: XLSXW to $(QA_EXCEL)

Note: Kontrolle ob BB-Art=12 (Moore) vorkommt. Muss von DDS gelöscht werden.
SQLCreator_11
    DATASET = $(NORM_DATABASE)
    EXPOSED_ATTRIBUTE_LIST = BFSNR,BBFID,ART
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.art, t.bfsnr, t.bbfid
        from mopube_bbf t
        where t.art = 12
       order by t.bfsnr asc, t.bbfid asc
    RESULT -> BBF_ART12 (writer XLSXW_1)
BBF_ART12 (writer XLSXW_1)
    attributes: BFSNR string(6), BBFID string(20), ART string(6)
Note: Kontrolle ob BB-Art= NULL vorkommt.
SQLCreator_70
    DATASET = $(NORM_DATABASE)
    EXPOSED_ATTRIBUTE_LIST = BFSNR,BBFID
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.art, t.bfsnr, t.bbfid
        from mopube_bbf t
        where t.art is NULL
       order by t.bfsnr asc
    RESULT -> BBF_ART_NULL (writer XLSXW_1)
BBF_ART_NULL (writer XLSXW_1)
    attributes: BFSNR number(6), BBFID string(20)
Note: Prüfft LIF ob Fiktive Geometrien vorkommen
SQLCreator_69
    DATASET = $(NORM_DATABASE)
    EXPOSED_ATTRIBUTE_LIST = BFSNR,GBKR,NUMMER
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, t.gbkr, t.nummer
        from mopube_lif t
         where t.nummer like '%fik%' or t.nummer like '%fic%'
      order by t.bfsnr
    RESULT -> LIF_FIKTIVE_Geometrien (writer XLSXW_1)
LIF_FIKTIVE_Geometrien (writer XLSXW_1)
    attributes: BFSNR number(6), GBKR number(5), NUMMER string(12)
Note: Prüfft BBTXT ob doppelte BEGIDS vorkommen
SQLCreator_6
    DATASET = $(NORM_DATABASE)
    EXPOSED_ATTRIBUTE_LIST = BEGID,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.nummername begid, count(*) anzahl
        from mopube_bbtxt t
          where t.typ = 0
          group by t.nummername
          having count(*) > 1
      order by t.nummername
    RESULT -> BBTXT_doppelte_BEGIDs (writer XLSXW_1)
BBTXT_doppelte_BEGIDs (writer XLSXW_1)
    attributes: BEGID string(20), ANZAHL number(10)
Note: Prüfft BBF und EOF ob doppelte EGID vorkommen
SQLCreator_8
    DATASET = $(NORM_DATABASE)
    EXPOSED_ATTRIBUTE_LIST = GWR_EGID,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select gwr_egid, count(*) anzahl
        from (
        select t.gwr_egid
        from mopube_bbf t
         where t.art = 0
         union all
         select t2.gwr_egid
        from mopube_eof t2
          where t2.art in (1, 6, 9, 11, 12, 16, 21)
        )
          group by gwr_egid
          having count(*) > 1
      order by gwr_egid
    RESULT -> BBF_EOF_doppelte_EGID (writer XLSXW_1)
BBF_EOF_doppelte_EGID (writer XLSXW_1)
    attributes: GWR_EGID string(20), ANZAHL number(12)
Note: Prüfft BBF ob doppelte BEGIDS vorkommen
SQLCreator_71
    DATASET = $(NORM_DATABASE)
    EXPOSED_ATTRIBUTE_LIST = BEGID,ANZAHL
    FORMAT = ORACLE8I_DB
    ORACLE8I_DB_PASSWORD = $(NORM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(NORM_USERNAME)
    ORACLE8I_DB_USE_UNIFIED_DATE_ATTRS = YES
    SQL_STATEMENT:
      select t.begid, count(*) anzahl
        from mopube_bbf t
          where t.art = 0
          group by t.begid
          having count(*) > 1
      order by t.begid
    RESULT -> BBF_doppelte_BEGIDs (writer XLSXW_1)
BBF_doppelte_BEGIDs (writer XLSXW_1)
    attributes: BEGID string(20), ANZAHL number(20)
Note: Prüfft BBF und EOF ob doppelte BEGIDS vorkommen
SQLCreator_7
    DATASET = $(NORM_DATABASE)
    EXPOSED_ATTRIBUTE_LIST = BEGID,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select begid, count(*) anzahl
        from (
        select t.begid
        from mopube_bbf t
         where t.art = 0
         union all
         select t2.begid
        from mopube_eof t2
          where t2.art in (1, 6, 9, 11, 12, 16, 21)
        )
          group by begid
          having count(*) > 1
      order by begid
    RESULT -> BBF_EOF_doppelte_BEGIDs (writer XLSXW_1)
BBF_EOF_doppelte_BEGIDs (writer XLSXW_1)
    attributes: BEGID string(20), ANZAHL number(12)

Bookmark: Vergleich Bodenbedeckung
Note: VEK1P
SQLCreator
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_bbf t group by t.bfsnr order by t.bfsnr asc
    RESULT -> StringConcatenator
StringConcatenator
    ACTION = Create New Attribute
    PARM_LINE = @Value(BFSNR)
    VAL_ATTR = TEMPKEY
    -> BulkAttributeRenamer
BulkAttributeRenamer
    ATTRCHOICE = All Attributes
    MODE_CHOICE = RENAME
    PATTERN_ACTION_DISP = ADDSUFFIX
    REPLACE_STR = _ALT
    -> FeatureMerger [REQUESTOR]
Note: TEAMP
SQLCreator_2
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_bbf t group by t.bfsnr order by t.bfsnr asc
    RESULT -> StringConcatenator_2
StringConcatenator_2
    ACTION = Create New Attribute
    PARM_LINE = @Value(BFSNR)
    VAL_ATTR = TEMPKEY
    -> BulkAttributeRenamer_2
BulkAttributeRenamer_2
    ATTRCHOICE = All Attributes
    MODE_CHOICE = RENAME
    PATTERN_ACTION_DISP = ADDSUFFIX
    REPLACE_STR = _NEU
    -> FeatureMerger [SUPPLIER]
FeatureMerger
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator
    UNMERGED_REQUESTOR -> verschwundeGDE_BBF (writer XLSXW_1)
    UNUSED_SUPPLIER -> hinzugekommeGDE_BBF (writer XLSXW_1)
ExpressionEvaluator
    ACTION = Create New Attribute
    EXPRESSION = (@Value(ANZAHL_NEU)-@Value(ANZAHL_ALT))
    VAL_ATTR = DIFF_ABS
    -> ExpressionEvaluator_2
ExpressionEvaluator_2
    ACTION = Create New Attribute
    EXPRESSION = (@Value(DIFF_ABS)/(@Value(ANZAHL_ALT)/100.0))
    VAL_ATTR = DIFF_REL
    -> Sorter
Sorter
    SORT_PARM = DIFF_ABS NUMERIC ASCENDING
    SORTED -> Statistik_BBF (writer XLSXW_1)
Statistik_BBF (writer XLSXW_1)
    attributes: BFSNR number(6), ANZAHL_ALT number(12), ANZAHL_NEU number(12), DIFF_ABS number(9), DIFF_REL number(9)
verschwundeGDE_BBF (writer XLSXW_1)
    attributes: BFSNR number(6), ANZAHL number(12)
hinzugekommeGDE_BBF (writer XLSXW_1)
    attributes: BFSNR number(6), ANZAHL number(12)

Bookmark: Vergleich Liegenschaften
Note: VEK1P
SQLCreator_9
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_lif t group by t.bfsnr order by t.bfsnr asc
    RESULT -> StringConcatenator_4
StringConcatenator_4
    ACTION = Create New Attribute
    PARM_LINE = @Value(BFSNR)
    VAL_ATTR = TEMPKEY
    -> BulkAttributeRenamer_4
BulkAttributeRenamer_4
    ATTRCHOICE = All Attributes
    MODE_CHOICE = RENAME
    PATTERN_ACTION_DISP = ADDSUFFIX
    REPLACE_STR = _ALT
    -> FeatureMerger_2 [REQUESTOR]
Note: TEAMP
SQLCreator_10
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_lif t group by t.bfsnr order by t.bfsnr asc
    RESULT -> StringConcatenator_3
StringConcatenator_3
    ACTION = Create New Attribute
    PARM_LINE = @Value(BFSNR)
    VAL_ATTR = TEMPKEY
    -> BulkAttributeRenamer_3
BulkAttributeRenamer_3
    ATTRCHOICE = All Attributes
    MODE_CHOICE = RENAME
    PATTERN_ACTION_DISP = ADDSUFFIX
    REPLACE_STR = _NEU
    -> FeatureMerger_2 [SUPPLIER]
FeatureMerger_2
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_3
    UNMERGED_REQUESTOR -> verschwundeGDE_LIF (writer XLSXW_1)
    UNUSED_SUPPLIER -> hinzugekommeGDE_LIF (writer XLSXW_1)
ExpressionEvaluator_3
    ACTION = Create New Attribute
    EXPRESSION = (@Value(ANZAHL_NEU)-@Value(ANZAHL_ALT))
    VAL_ATTR = DIFF_ABS
    -> ExpressionEvaluator_4
ExpressionEvaluator_4
    ACTION = Create New Attribute
    EXPRESSION = (@Value(DIFF_ABS)/(@Value(ANZAHL_ALT)/100.0))
    VAL_ATTR = DIFF_REL
    -> Sorter_2
Sorter_2
    SORT_PARM = DIFF_ABS NUMERIC ASCENDING
    SORTED -> Statistik_LIF (writer XLSXW_1)
Statistik_LIF (writer XLSXW_1)
    attributes: BFSNR number(6), ANZAHL_ALT number(12), ANZAHL_NEU number(12), DIFF_ABS number(9), DIFF_REL number(9)
verschwundeGDE_LIF (writer XLSXW_1)
    attributes: BFSNR number(6), ANZAHL number(12)
hinzugekommeGDE_LIF (writer XLSXW_1)
    attributes: BFSNR number(6), ANZAHL number(12)

Bookmark: Doppelte Gemeindegrenzen
Note: TEAMP
SQLCreator_85
    DATASET = $(NORM_DATABASE)
    EXPOSED_ATTRIBUTE_LIST = BFSNR,Area,GEMNAME
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      SELECT
          mopube_hgf.bfsnr, mopube_hgf.sde.st_area (shape) as "Area", mopube_hgf.gemname
      FROM
          mopube_hgf
      INNER JOIN ( SELECT bfsnr FROM     mopube_hgf
      group by
          bfsnr

      HAVING
          COUNT(*) > 1) dup ON mopube_hgf.bfsnr = dup.bfsnr
    RESULT -> AttributeRounder
AttributeRounder
    PLACES = 0
    ROUND_TYPE = Nearest
    SRC_ATTRS = Area
    -> DuplicateFilter
Note: identische Flächen?
DuplicateFilter
    INPUT_ORDERED_CHOICE = No
    KEYATTR = Area
    DUPLICATE -> doppelteHGF (writer XLSXW_1)
doppelteHGF (writer XLSXW_1)
    attributes: BFSNR number(6), GEMNAME string(100)

Bookmark: Kontrolle ob NULL-Geometrien existieren (alle Linien und Flächen FCs)
Note: Prüfft BBF ob NULL Geometrien vorkommen
SQLCreator_5
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_bbf t
        where sde.st_area (shape) is NULL
       GROUP BY t.BFSNR
       order by t.bfsnr
    RESULT -> BBF_NULL_Geometrien (writer XLSXW_1)
BBF_NULL_Geometrien (writer XLSXW_1)
    attributes: BFSNR number(6), ANZAHL number(12)
Note: Prüfft BBPRJF ob NULL Geometrien vorkommen
SQLCreator_54
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_bbprjf t
        where sde.st_area (shape) is NULL
       GROUP BY t.BFSNR
       order by t.bfsnr
    RESULT -> BBPRJF_NULL_Geometrien (writer XLSXW_1)
BBPRJF_NULL_Geometrien (writer XLSXW_1)
    attributes: BFSNR number(6), ANZAHL number(12)
Note: Prüfft EOF ob NULL Geometrien vorkommen
SQLCreator_55
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_eof t
          where sde.st_area (shape) is NULL
       GROUP BY t.BFSNR
       order by t.bfsnr
    RESULT -> EOF_NULL_Geometrien (writer XLSXW_1)
EOF_NULL_Geometrien (writer XLSXW_1)
    attributes: BFSNR number(6), ANZAHL number(12)
Note: Prüfft EOL ob NULL Geometrien vorkommen
SQLCreator_56
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_eol t
        where sde.st_length (shape) is NULL
       GROUP BY t.BFSNR
       order by t.bfsnr
    RESULT -> EOL_NULL_Geometrien (writer XLSXW_1)
EOL_NULL_Geometrien (writer XLSXW_1)
    attributes: BFSNR number(6), ANZAHL number(12)
Note: Prüfft HGABSCHL ob NULL Geometrien vorkommen
SQLCreator_57
    DATASET = $(NORM_DATABASE)
    EXPOSED_ATTRIBUTE_LIST = TYP,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.typ, count(*) anzahl
        from mopube_hgabschl t
        where sde.st_length (shape) is NULL
       GROUP BY t.typ
    RESULT -> HGABSCHL_NULL_Geometrien (writer XLSXW_1)
HGABSCHL_NULL_Geometrien (writer XLSXW_1)
    attributes: TYP number(6), ANZAHL number(12)
Note: Prüfft HGF ob NULL Geometrien vorkommen
SQLCreator_58
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_hgf t
          where sde.st_area (shape) is NULL
       GROUP BY t.BFSNR
       order by t.bfsnr
    RESULT -> HGF_NULL_Geometrien (writer XLSXW_1)
HGF_NULL_Geometrien (writer XLSXW_1)
    attributes: BFSNR number(6), ANZAHL number(12)
Note: Prüfft HGL ob NULL Geometrien vorkommen
SQLCreator_59
    DATASET = $(NORM_DATABASE)
    EXPOSED_ATTRIBUTE_LIST = LINIENART,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.linienart, count(*) anzahl
        from mopube_hgl t
        where sde.st_length (shape) is NULL
       GROUP BY t.linienart
    RESULT -> HGL_NULL_Geometrien (writer XLSXW_1)
HGL_NULL_Geometrien (writer XLSXW_1)
    attributes: LINIENART number(10), ANZAHL number(12)
Note: Prüfft HGPRJF ob NULL Geometrien vorkommen
SQLCreator_60
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_hgprjf t
        where sde.st_length (shape) is NULL
       GROUP BY t.bfsnr
    RESULT -> HGPRJF_NULL_Geometrien (writer XLSXW_1)
HGPRJF_NULL_Geometrien (writer XLSXW_1)
    attributes: BFSNR number(6), ANZAHL number(12)
Note: Prüfft LIF ob NULL Geometrien vorkommen
SQLCreator_25
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_lif t
        where sde.st_area (shape) is NULL
       GROUP BY t.BFSNR
       order by t.bfsnr
    RESULT -> LIF_NULL_Geometrien (writer XLSXW_1)
LIF_NULL_Geometrien (writer XLSXW_1)
    attributes: BFSNR number(6), ANZAHL number(12)
Note: Prüfft LIL ob NULL Geometrien vorkommen
SQLCreator_61
    DATASET = $(NORM_DATABASE)
    EXPOSED_ATTRIBUTE_LIST = LINIENART,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.linienart, count(*) anzahl
        from mopube_lil t
        where sde.st_length (shape) is NULL
       GROUP BY t.linienart
    RESULT -> LIL_NULL_Geometrien (writer XLSXW_1)
LIL_NULL_Geometrien (writer XLSXW_1)
    attributes: LINIENART number(10), ANZAHL number(12)
Note: Prüfft LIPRJF ob NULL Geometrien vorkommen
SQLCreator_62
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_liprjf t
        where sde.st_area (shape) is NULL
       GROUP BY t.BFSNR
       order by t.bfsnr
    RESULT -> LIPRJF_NULL_Geometrien (writer XLSXW_1)
LIPRJF_NULL_Geometrien (writer XLSXW_1)
    attributes: BFSNR number(6), ANZAHL number(12)
Note: Prüfft LISRF ob NULL Geometrien vorkommen
SQLCreator_63
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_lisrf t
        where sde.st_area (shape) is NULL
       GROUP BY t.BFSNR
       order by t.bfsnr
    RESULT -> LISRF_NULL_Geometrien (writer XLSXW_1)
LISRF_NULL_Geometrien (writer XLSXW_1)
    attributes: BFSNR number(6), ANZAHL number(12)
Note: Prüfft LISRL ob NULL Geometrien vorkommen
SQLCreator_64
    DATASET = $(NORM_DATABASE)
    EXPOSED_ATTRIBUTE_LIST = LINIENART,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.linienart, count(*) anzahl
        from mopube_lisrl t
        where sde.st_length (shape) is NULL
       GROUP BY t.linienart
    RESULT -> LISRL_NULL_Geometrien (writer XLSXW_1)
LISRL_NULL_Geometrien (writer XLSXW_1)
    attributes: LINIENART number(10), ANZAHL number(12)
Note: Prüfft LISRPRJF ob NULL Geometrien vorkommen
SQLCreator_65
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_lisrprjf t
        where sde.st_area (shape) is NULL
       GROUP BY t.BFSNR
       order by t.bfsnr
    RESULT -> LISRPRJF_NULL_Geometrien (writer XLSXW_1)
LISRPRJF_NULL_Geometrien (writer XLSXW_1)
    attributes: BFSNR number(6), ANZAHL number(12)
Note: Prüfft NONAMF ob NULL Geometrien vorkommen
SQLCreator_66
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_nonamf t
        where sde.st_area (shape) is NULL
       GROUP BY t.BFSNR
       order by t.bfsnr
    RESULT -> NONAMF_NULL_Geometrien (writer XLSXW_1)
NONAMF_NULL_Geometrien (writer XLSXW_1)
    attributes: BFSNR number(6), ANZAHL number(12)
Note: Prüfft RLF ob NULL Geometrien vorkommen
SQLCreator_67
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_rlf t
        where sde.st_area (shape) is NULL
       GROUP BY t.BFSNR
       order by t.bfsnr
    RESULT -> RLF_NULL_Geometrien (writer XLSXW_1)
RLF_NULL_Geometrien (writer XLSXW_1)
    attributes: BFSNR number(6), ANZAHL number(12)
Note: Prüfft RLL ob NULL Geometrien vorkommen
SQLCreator_68
    DATASET = $(NORM_DATABASE)
    EXPOSED_ATTRIBUTE_LIST = LINIENART,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.bfsnr, count(*) anzahl
        from mopube_rll t
        where sde.st_length (shape) is NULL
       GROUP BY t.bfsnr
    RESULT -> RLL_NULL_Geometrien (writer XLSXW_1)
RLL_NULL_Geometrien (writer XLSXW_1)
    attributes: LINIENART number(10), ANZAHL number(12)

Bookmark: Vergleich Nomenklatur
Note: VEK1P
SQLCreator_82
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_NONAMF t group by t.bfsnr order by t.bfsnr asc
    RESULT -> StringConcatenator_16
StringConcatenator_16
    ACTION = Create New Attribute
    PARM_LINE = @Value(BFSNR)
    VAL_ATTR = TEMPKEY
    -> BulkAttributeRenamer_16
BulkAttributeRenamer_16
    ATTRCHOICE = All Attributes
    MODE_CHOICE = RENAME
    PATTERN_ACTION_DISP = ADDSUFFIX
    REPLACE_STR = _ALT
    -> FeatureMerger_8 [REQUESTOR]
Note: TEAMP
SQLCreator_83
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_NONAMF t group by t.bfsnr order by t.bfsnr asc
    RESULT -> StringConcatenator_15
StringConcatenator_15
    ACTION = Create New Attribute
    PARM_LINE = @Value(BFSNR)
    VAL_ATTR = TEMPKEY
    -> BulkAttributeRenamer_15
BulkAttributeRenamer_15
    ATTRCHOICE = All Attributes
    MODE_CHOICE = RENAME
    PATTERN_ACTION_DISP = ADDSUFFIX
    REPLACE_STR = _NEU
    -> FeatureMerger_8 [SUPPLIER]
FeatureMerger_8
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_16
    UNMERGED_REQUESTOR -> verschwundeGDE_NONAMF (writer XLSXW_1)
    UNUSED_SUPPLIER -> hinzugekommeGDE_NONAMF (writer XLSXW_1)
ExpressionEvaluator_16
    ACTION = Create New Attribute
    EXPRESSION = (@Value(ANZAHL_NEU)-@Value(ANZAHL_ALT))
    VAL_ATTR = DIFF_ABS
    -> ExpressionEvaluator_15
ExpressionEvaluator_15
    ACTION = Create New Attribute
    EXPRESSION = (@Value(DIFF_ABS)/(@Value(ANZAHL_ALT)/100.0))
    VAL_ATTR = DIFF_REL
    -> Sorter_8
Sorter_8
    SORT_PARM = DIFF_ABS NUMERIC ASCENDING
    SORTED -> Statistik_NONAMF (writer XLSXW_1)
Statistik_NONAMF (writer XLSXW_1)
    attributes: BFSNR number(6), ANZAHL_ALT number(12), ANZAHL_NEU number(12), DIFF_ABS number(9), DIFF_REL number(9)
verschwundeGDE_NONAMF (writer XLSXW_1)
    attributes: BFSNR number(6), ANZAHL number(12)
hinzugekommeGDE_NONAMF (writer XLSXW_1)
    attributes: BFSNR number(6), ANZAHL number(12)

Bookmark: Vergleich Fixpunkte
Note: VEK1P
SQLCreator_72
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_fixp t group by t.bfsnr order by t.bfsnr asc
    RESULT -> StringConcatenator_6
StringConcatenator_6
    ACTION = Create New Attribute
    PARM_LINE = @Value(BFSNR)
    VAL_ATTR = TEMPKEY
    -> BulkAttributeRenamer_6
BulkAttributeRenamer_6
    ATTRCHOICE = All Attributes
    MODE_CHOICE = RENAME
    PATTERN_ACTION_DISP = ADDSUFFIX
    REPLACE_STR = _ALT
    -> FeatureMerger_3 [REQUESTOR]
Note: TEAMP
SQLCreator_73
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_fixp t group by t.bfsnr order by t.bfsnr asc
    RESULT -> StringConcatenator_5
StringConcatenator_5
    ACTION = Create New Attribute
    PARM_LINE = @Value(BFSNR)
    VAL_ATTR = TEMPKEY
    -> BulkAttributeRenamer_5
BulkAttributeRenamer_5
    ATTRCHOICE = All Attributes
    MODE_CHOICE = RENAME
    PATTERN_ACTION_DISP = ADDSUFFIX
    REPLACE_STR = _NEU
    -> FeatureMerger_3 [SUPPLIER]
FeatureMerger_3
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_6
    UNMERGED_REQUESTOR -> verschwundeGDE_FIXP (writer XLSXW_1)
    UNUSED_SUPPLIER -> hinzugekommeGDE_FIXP (writer XLSXW_1)
ExpressionEvaluator_6
    ACTION = Create New Attribute
    EXPRESSION = (@Value(ANZAHL_NEU)-@Value(ANZAHL_ALT))
    VAL_ATTR = DIFF_ABS
    -> ExpressionEvaluator_5
ExpressionEvaluator_5
    ACTION = Create New Attribute
    EXPRESSION = (@Value(DIFF_ABS)/(@Value(ANZAHL_ALT)/100.0))
    VAL_ATTR = DIFF_REL
    -> Sorter_3
Sorter_3
    SORT_PARM = DIFF_ABS NUMERIC ASCENDING
    SORTED -> Statistik_FIXP (writer XLSXW_1)
Statistik_FIXP (writer XLSXW_1)
    attributes: BFSNR number(6), ANZAHL_ALT number(12), ANZAHL_NEU number(12), DIFF_ABS number(9), DIFF_REL number(9)
verschwundeGDE_FIXP (writer XLSXW_1)
    attributes: BFSNR number(6), ANZAHL number(12)
hinzugekommeGDE_FIXP (writer XLSXW_1)
    attributes: BFSNR number(6), ANZAHL number(12)

Bookmark: Vergleich EO-Flächen
Note: VEK1P
SQLCreator_74
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_eof t group by t.bfsnr order by t.bfsnr asc
    RESULT -> StringConcatenator_8
StringConcatenator_8
    ACTION = Create New Attribute
    PARM_LINE = @Value(BFSNR)
    VAL_ATTR = TEMPKEY
    -> BulkAttributeRenamer_8
BulkAttributeRenamer_8
    ATTRCHOICE = All Attributes
    MODE_CHOICE = RENAME
    PATTERN_ACTION_DISP = ADDSUFFIX
    REPLACE_STR = _ALT
    -> FeatureMerger_4 [REQUESTOR]
Note: TEAMP
SQLCreator_75
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_eof t group by t.bfsnr order by t.bfsnr asc
    RESULT -> StringConcatenator_7
StringConcatenator_7
    ACTION = Create New Attribute
    PARM_LINE = @Value(BFSNR)
    VAL_ATTR = TEMPKEY
    -> BulkAttributeRenamer_7
BulkAttributeRenamer_7
    ATTRCHOICE = All Attributes
    MODE_CHOICE = RENAME
    PATTERN_ACTION_DISP = ADDSUFFIX
    REPLACE_STR = _NEU
    -> FeatureMerger_4 [SUPPLIER]
FeatureMerger_4
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_8
    UNMERGED_REQUESTOR -> verschwundeGDE_EOF (writer XLSXW_1)
    UNUSED_SUPPLIER -> hinzugekommeGDE_EOF (writer XLSXW_1)
ExpressionEvaluator_8
    ACTION = Create New Attribute
    EXPRESSION = (@Value(ANZAHL_NEU)-@Value(ANZAHL_ALT))
    VAL_ATTR = DIFF_ABS
    -> ExpressionEvaluator_7
ExpressionEvaluator_7
    ACTION = Create New Attribute
    EXPRESSION = (@Value(DIFF_ABS)/(@Value(ANZAHL_ALT)/100.0))
    VAL_ATTR = DIFF_REL
    -> Sorter_4
Sorter_4
    SORT_PARM = DIFF_ABS NUMERIC ASCENDING
    SORTED -> Statistik_EOF (writer XLSXW_1)
Statistik_EOF (writer XLSXW_1)
    attributes: BFSNR number(6), ANZAHL_ALT number(12), ANZAHL_NEU number(12), DIFF_ABS number(9), DIFF_REL number(9)
verschwundeGDE_EOF (writer XLSXW_1)
    attributes: BFSNR number(6), ANZAHL number(12)
hinzugekommeGDE_EOF (writer XLSXW_1)
    attributes: BFSNR number(6), ANZAHL number(12)

Bookmark: Kontrolle ob BFSNR abgefüllt ist
Note: Prüft, ob alle BFS-Nr in FIX abgefüllt sind
SQLCreator_22
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t.BFSNR, count(*) anzahl
        from MOPUBE_FIXP t
        where t.BFSNR is null
        GROUP BY t.BFSNR
    RESULT -> FIX_BFSNR_NULL (writer XLSXW_1)
FIX_BFSNR_NULL (writer XLSXW_1)
    attributes: BFSNR number(6), ANZAHL number(12)
Note: Prüft, ob alle BFS-Nr in BBF abgefüllt sind
SQLCreator_4
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(bbfid,1,3) as bfsnrneu, count(*)
        from mopube_bbf
        where bfsnr is null
        group by substr(bbfid,1,3)
    RESULT -> BBF_BFSNR_NULL (writer XLSXW_1)
BBF_BFSNR_NULL (writer XLSXW_1)
    attributes: BFSNRNEU number(6), ANZAHL number(12)
Note: Prüft, ob alle BFS-Nr in BBTXT abgefüllt sind
SQLCreator_23
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(bbfid,1,3) as bfsnrneu, count(*)
        from mopube_bbtxt
        where bfsnr is null
        group by substr(bbfid,1,3)
    RESULT -> BBTXT_BFSNR_NULL (writer XLSXW_1)
BBTXT_BFSNR_NULL (writer XLSXW_1)
    attributes: BFSNRNEU number(6), ANZAHL number(12)
Note: Prüft, ob alle BFS-Nr in BBPRJF abgefüllt sind
SQLCreator_3
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(bbprjfid,1,3) as bfsnrneu, count(*) anzahl
        from mopube_bbprjf
        where bfsnr is null
        group by substr(bbprjfid,1,3)
    RESULT -> BBPRJF_BFSNR_NULL (writer XLSXW_1)
BBPRJF_BFSNR_NULL (writer XLSXW_1)
    attributes: BFSNRNEU number(6), ANZAHL number(12)
Note: Prüft, ob alle BFS-Nr in BBPRJTXT abgefüllt sind
SQLCreator_12
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(bbprjfid,1,3) as bfsnrneu, count(*) anzahl
        from mopube_bbprjtxt
        where bfsnr is null
        group by substr(bbprjfid,1,3)
    RESULT -> BBPRJTXT_BFSNR_NULL (writer XLSXW_1)
BBPRJTXT_BFSNR_NULL (writer XLSXW_1)
    attributes: BFSNRNEU number(6), ANZAHL number(12)
Note: Prüft, ob alle BFS-Nr in EOF abgefüllt sind
SQLCreator_24
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eofid,1,3) as bfsnrneu, count(*) anzahl
        from mopube_eof
        where bfsnr is null
        group by substr(eofid,1,3)
    RESULT -> EOF_BFSNR_NULL (writer XLSXW_1)
EOF_BFSNR_NULL (writer XLSXW_1)
    attributes: BFSNRNEU number(6), ANZAHL number(12)
Note: Prüft, ob alle BFS-Nr in EOFTXT abgefüllt sind
SQLCreator_26
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eofid,1,3) as bfsnrneu, count(*) anzahl
        from mopube_eoftxt
        where bfsnr is null
        group by substr(eofid,1,3)
    RESULT -> EOFTXT_BFSNR_NULL (writer XLSXW_1)
EOFTXT_BFSNR_NULL (writer XLSXW_1)
    attributes: BFSNRNEU number(6), ANZAHL number(12)
Note: Prüft, ob alle BFS-Nr in EOL abgefüllt sind
SQLCreator_27
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eolid,1,3) as bfsnrneu, count(*) anzahl
        from mopube_eol
        where bfsnr is null
        group by substr(eolid,1,3)
    RESULT -> EOL_BFSNR_NULL (writer XLSXW_1)
EOL_BFSNR_NULL (writer XLSXW_1)
    attributes: BFSNRNEU number(6), ANZAHL number(12)
Note: Prüft, ob alle BFS-Nr in EOLTXT abgefüllt sind
SQLCreator_28
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eolid,1,3) as bfsnrneu, count(*) anzahl
        from mopube_eoltxt
        where bfsnr is null
        group by substr(eolid,1,3)
    RESULT -> EOLTXT_BFSNR_NULL (writer XLSXW_1)
EOLTXT_BFSNR_NULL (writer XLSXW_1)
    attributes: BFSNRNEU number(6), ANZAHL number(12)
Note: Prüft, ob alle BFS-Nr in EOP abgefüllt sind
SQLCreator_29
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eopid,1,3) as bfsnrneu, count(*) anzahl
        from mopube_eop
        where bfsnr is null
        group by substr(eopid,1,3)
    RESULT -> EOP_BFSNR_NULL (writer XLSXW_1)
EOP_BFSNR_NULL (writer XLSXW_1)
    attributes: BFSNRNEU number(6), ANZAHL number(12)
Note: Prüft, ob alle BFS-Nr in EOPTXT abgefüllt sind
SQLCreator_30
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(eopid,1,3) as bfsnrneu, count(*) anzahl
        from mopube_eoptxt
        where bfsnr is null
        group by substr(eopid,1,3)
    RESULT -> EOPTXT_BFSNR_NULL (writer XLSXW_1)
EOPTXT_BFSNR_NULL (writer XLSXW_1)
    attributes: BFSNRNEU number(6), ANZAHL number(12)
Note: Prüft, ob alle BFS-Nr in NOMAMTXT abgefüllt sind
SQLCreator_33
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(nonamfid,1,3) as bfsnrneu, count(*) anzahl
        from mopube_nonamtxt
        where bfsnr is null
        group by substr(nonamfid,1,3)
    RESULT -> NONAMTXT_BFSNR_NULL (writer XLSXW_1)
NONAMTXT_BFSNR_NULL (writer XLSXW_1)
    attributes: BFSNRNEU number(6), ANZAHL number(12)
Note: Prüft, ob alle BFS-Nr in LIGP abgefüllt sind
SQLCreator_34
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select bfsnr, count(*) anzahl
        from mopube_ligp
        where bfsnr is null
        group by bfsnr
    RESULT -> LIGP_BFSNR_NULL (writer XLSXW_1)
LIGP_BFSNR_NULL (writer XLSXW_1)
    attributes: BFSNRNEU number(6), ANZAHL number(12)
Note: Prüft, ob alle BFS-Nr in RLF abgefüllt sind
SQLCreator_42
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(rlfid,1,3) as bfsnrneu, count(*) anzahl
        from mopube_rlf
        where bfsnr is null
        group by substr(rlfid,1,3)
    RESULT -> RLF_BFSNR_NULL (writer XLSXW_1)
RLF_BFSNR_NULL (writer XLSXW_1)
    attributes: BFSNRNEU number(6), ANZAHL number(12)
Note: Prüft, ob alle BFS-Nr in RLFTXT abgefüllt sind
SQLCreator_43
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(rlfid,1,3) as bfsnrneu, count(*) anzahl
        from mopube_rlftxt
        where bfsnr is null
        group by substr(rlfid,1,3)
    RESULT -> RLFTXT_BFSNR_NULL (writer XLSXW_1)
RLFTXT_BFSNR_NULL (writer XLSXW_1)
    attributes: BFSNRNEU number(6), ANZAHL number(12)
Note: Prüft, ob alle BFS-Nr in RLL abgefüllt sind
SQLCreator_44
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(rllid,1,3) as bfsnrneu, count(*) anzahl
        from mopube_rll
        where bfsnr is null
        group by substr(rllid,1,3)
    RESULT -> RLL_BFSNR_NULL (writer XLSXW_1)
RLL_BFSNR_NULL (writer XLSXW_1)
    attributes: BFSNRNEU number(6), ANZAHL number(12)
Note: Prüft, ob alle BFS-Nr in RLLTXT abgefüllt sind
SQLCreator_45
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(rllid,1,3) as bfsnrneu, count(*) anzahl
        from mopube_rlltxt
        where bfsnr is null
        group by substr(rllid,1,3)
    RESULT -> RLLTXT_BFSNR_NULL (writer XLSXW_1)
RLLTXT_BFSNR_NULL (writer XLSXW_1)
    attributes: BFSNRNEU number(6), ANZAHL number(12)
Note: Prüft, ob alle BFS-Nr in RLP abgefüllt sind
SQLCreator_46
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select bfsnr, count(*) anzahl
        from mopube_rlp
        where bfsnr is null
        group by bfsnr
    RESULT -> RLP_BFSNR_NULL (writer XLSXW_1)
RLP_BFSNR_NULL (writer XLSXW_1)
    attributes: BFSNRNEU number(6), ANZAHL number(12)
Note: Prüft, ob alle BFS-Nr in HGP abgefüllt sind
SQLCreator_47
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select bfsnr, count(*) anzahl
        from mopube_hgp
        where bfsnr is null
        group by bfsnr
    RESULT -> HGP_BFSNR_NULL (writer XLSXW_1)
HGP_BFSNR_NULL (writer XLSXW_1)
    attributes: BFSNRNEU number(6), ANZAHL number(12)
Note: Prüft, ob alle BFS-Nr in HGF abgefüllt sind
SQLCreator_48
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select bfsnr, count(*) anzahl
        from mopube_hgf
        where bfsnr is null
        group by bfsnr
    RESULT -> HGF_BFSNR_NULL (writer XLSXW_1)
HGF_BFSNR_NULL (writer XLSXW_1)
    attributes: BFSNRNEU number(6), ANZAHL number(12)
Note: Prüft, ob alle BFS-Nr in HGPPRJ abgefüllt sind
SQLCreator_49
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select bfsnr, count(*) anzahl
        from mopube_hgprjf
        where bfsnr is null
        group by bfsnr
    RESULT -> HGPPRJF_BFSNR_NULL (writer XLSXW_1)
HGPPRJF_BFSNR_NULL (writer XLSXW_1)
    attributes: BFSNRNEU number(6), ANZAHL number(12)
Note: Prüft, ob alle BFS-Nr in GASTRNA abgefüllt sind
SQLCreator_50
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(gastrna,1,3) as bfsnrneu, count(*) anzahl
        from mopube_gastrna
        where bfsnr is null
        group by substr(gastrna,1,3)
    RESULT -> GASTRNA_BFSNR_NULL (writer XLSXW_1)
GASTRNA_BFSNR_NULL (writer XLSXW_1)
    attributes: BFSNRNEU number(6), ANZAHL number(12)
Note: Prüft, ob alle BFS-Nr in GASTRNAT abgefüllt sind
SQLCreator_51
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(gastrna,1,3) as bfsnrneu, count(*) anzahl
        from mopube_gastrnat
        where bfsnr is null
        group by substr(gastrna,1,3)
    RESULT -> GASTRNAT_BFSNR_NULL (writer XLSXW_1)
GASTRNAT_BFSNR_NULL (writer XLSXW_1)
    attributes: BFSNRNEU number(6), ANZAHL number(12)
Note: Prüft, ob alle BFS-Nr in GAEINP abgefüllt sind
SQLCreator_52
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(gastrna,1,3) as bfsnrneu, count(*) anzahl
        from mopube_gaeinp
        where bfsnr is null
        group by substr(gastrna,1,3)
    RESULT -> GAEINP_BFSNR_NULL (writer XLSXW_1)
GAEINP_BFSNR_NULL (writer XLSXW_1)
    attributes: BFSNRNEU number(6), ANZAHL number(12)
Note: Prüft, ob alle BFS-Nr in GAEINTXT abgefüllt sind
SQLCreator_53
    DATASET = $(NORM_DATABASE)
    EXPOSED_ATTRIBUTE_LIST = BFSNRNEU,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select substr(gaeinp,1,3) as bfsnrneu, count(*) anzahl
        from mopube_gaeintxt
        where bfsnr is null
        group by substr(gaeinp,1,3)
    RESULT -> GAEINTXT_BFSNR_NULL (writer XLSXW_1)
GAEINTXT_BFSNR_NULL (writer XLSXW_1)
    attributes: BFSNRNEU number(6), ANZAHL number(12)

Bookmark: Vergleich Grenzpunkte
Note: VEK1P
SQLCreator_80
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_LIGP t group by t.bfsnr order by t.bfsnr asc
    RESULT -> StringConcatenator_14
StringConcatenator_14
    ACTION = Create New Attribute
    PARM_LINE = @Value(BFSNR)
    VAL_ATTR = TEMPKEY
    -> BulkAttributeRenamer_14
BulkAttributeRenamer_14
    ATTRCHOICE = All Attributes
    MODE_CHOICE = RENAME
    PATTERN_ACTION_DISP = ADDSUFFIX
    REPLACE_STR = _ALT
    -> FeatureMerger_7 [REQUESTOR]
Note: TEAMP
SQLCreator_81
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_LIGP t group by t.bfsnr order by t.bfsnr asc
    RESULT -> StringConcatenator_13
StringConcatenator_13
    ACTION = Create New Attribute
    PARM_LINE = @Value(BFSNR)
    VAL_ATTR = TEMPKEY
    -> BulkAttributeRenamer_13
BulkAttributeRenamer_13
    ATTRCHOICE = All Attributes
    MODE_CHOICE = RENAME
    PATTERN_ACTION_DISP = ADDSUFFIX
    REPLACE_STR = _NEU
    -> FeatureMerger_7 [SUPPLIER]
FeatureMerger_7
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_14
    UNMERGED_REQUESTOR -> verschwundeGDE_LIGP (writer XLSXW_1)
    UNUSED_SUPPLIER -> hinzugekommeGDE_LIGP (writer XLSXW_1)
ExpressionEvaluator_14
    ACTION = Create New Attribute
    EXPRESSION = (@Value(ANZAHL_NEU)-@Value(ANZAHL_ALT))
    VAL_ATTR = DIFF_ABS
    -> ExpressionEvaluator_13
ExpressionEvaluator_13
    ACTION = Create New Attribute
    EXPRESSION = (@Value(DIFF_ABS)/(@Value(ANZAHL_ALT)/100.0))
    VAL_ATTR = DIFF_REL
    -> Sorter_7
Sorter_7
    SORT_PARM = DIFF_ABS NUMERIC ASCENDING
    SORTED -> Statistik_LIGP (writer XLSXW_1)
Statistik_LIGP (writer XLSXW_1)
    attributes: BFSNR number(6), ANZAHL_ALT number(12), ANZAHL_NEU number(12), DIFF_ABS number(9), DIFF_REL number(9)
verschwundeGDE_LIGP (writer XLSXW_1)
    attributes: BFSNR number(6), ANZAHL number(12)
hinzugekommeGDE_LIGP (writer XLSXW_1)
    attributes: BFSNR number(6), ANZAHL number(12)

Bookmark: Vergleich EO-Linien
Note: VEK1P
SQLCreator_76
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_eol t group by t.bfsnr order by t.bfsnr asc
    RESULT -> StringConcatenator_10
StringConcatenator_10
    ACTION = Create New Attribute
    PARM_LINE = @Value(BFSNR)
    VAL_ATTR = TEMPKEY
    -> BulkAttributeRenamer_10
BulkAttributeRenamer_10
    ATTRCHOICE = All Attributes
    MODE_CHOICE = RENAME
    PATTERN_ACTION_DISP = ADDSUFFIX
    REPLACE_STR = _ALT
    -> FeatureMerger_5 [REQUESTOR]
Note: TEAMP
SQLCreator_77
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_eol t group by t.bfsnr order by t.bfsnr asc
    RESULT -> StringConcatenator_9
StringConcatenator_9
    ACTION = Create New Attribute
    PARM_LINE = @Value(BFSNR)
    VAL_ATTR = TEMPKEY
    -> BulkAttributeRenamer_9
BulkAttributeRenamer_9
    ATTRCHOICE = All Attributes
    MODE_CHOICE = RENAME
    PATTERN_ACTION_DISP = ADDSUFFIX
    REPLACE_STR = _NEU
    -> FeatureMerger_5 [SUPPLIER]
FeatureMerger_5
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_10
    UNMERGED_REQUESTOR -> verschwundeGDE_EOL (writer XLSXW_1)
    UNUSED_SUPPLIER -> hinzugekommeGDE_EOL (writer XLSXW_1)
ExpressionEvaluator_10
    ACTION = Create New Attribute
    EXPRESSION = (@Value(ANZAHL_NEU)-@Value(ANZAHL_ALT))
    VAL_ATTR = DIFF_ABS
    -> ExpressionEvaluator_9
ExpressionEvaluator_9
    ACTION = Create New Attribute
    EXPRESSION = (@Value(DIFF_ABS)/(@Value(ANZAHL_ALT)/100.0))
    VAL_ATTR = DIFF_REL
    -> Sorter_5
Sorter_5
    SORT_PARM = DIFF_ABS NUMERIC ASCENDING
    SORTED -> Statistik_EOL (writer XLSXW_1)
Statistik_EOL (writer XLSXW_1)
    attributes: BFSNR number(6), ANZAHL_ALT number(12), ANZAHL_NEU number(12), DIFF_ABS number(9), DIFF_REL number(9)
verschwundeGDE_EOL (writer XLSXW_1)
    attributes: BFSNR number(6), ANZAHL number(12)
hinzugekommeGDE_EOL (writer XLSXW_1)
    attributes: BFSNR number(6), ANZAHL number(12)

Bookmark: Vergleich EO-Punkte
Note: VEK1P
SQLCreator_78
    DATASET = $(VEK1_DATABASE)
    EXPOSED_ATTRIBUTE_LIST = BFSNR,ANZAHL
    FORMAT = ORACLE_NONSPATIAL
    ORACLE_NONSPATIAL_PASSWORD = $(VEK1_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(VEK1_USERNAME)
    ORACLE_NONSPATIAL_USE_UNIFIED_DATE_ATTRS = YES
    SQL_STATEMENT = select t.bfsnr, count(*) anzahl from geodb.mopube_eop t group by t.bfsnr order by t.bfsnr asc
    RESULT -> StringConcatenator_12
StringConcatenator_12
    ACTION = Create New Attribute
    PARM_LINE = @Value(BFSNR)
    VAL_ATTR = TEMPKEY
    -> BulkAttributeRenamer_12
BulkAttributeRenamer_12
    ATTRCHOICE = All Attributes
    MODE_CHOICE = RENAME
    PATTERN_ACTION_DISP = ADDSUFFIX
    REPLACE_STR = _ALT
    -> FeatureMerger_6 [REQUESTOR]
Note: TEAMP
SQLCreator_79
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT = select t.bfsnr, count(*) anzahl from mopube_eop t group by t.bfsnr order by t.bfsnr asc
    RESULT -> StringConcatenator_11
StringConcatenator_11
    ACTION = Create New Attribute
    PARM_LINE = @Value(BFSNR)
    VAL_ATTR = TEMPKEY
    -> BulkAttributeRenamer_11
BulkAttributeRenamer_11
    ATTRCHOICE = All Attributes
    MODE_CHOICE = RENAME
    PATTERN_ACTION_DISP = ADDSUFFIX
    REPLACE_STR = _NEU
    -> FeatureMerger_6 [SUPPLIER]
FeatureMerger_6
    ATTR_ACCUM_MODE = Merge Supplier
    ATTR_CONFLICT_RES = Use Requestor
    IGNORE_NULLS = No
    JOIN_KEYS = @Value(TEMPKEY_ALT) @Value(TEMPKEY_NEU) AUTO
    MERGE_TYPE = Attributes Only
    PROCESS_DUPS = NO
    REJECT_NULL_MISSING_KEYS = No
    SUPPLIERS_FIRST = No
    MERGED -> ExpressionEvaluator_12
    UNMERGED_REQUESTOR -> verschwundeGDE_EOP (writer XLSXW_1)
    UNUSED_SUPPLIER -> hinzugekommeGDE_EOP (writer XLSXW_1)
ExpressionEvaluator_12
    ACTION = Create New Attribute
    EXPRESSION = (@Value(ANZAHL_NEU)-@Value(ANZAHL_ALT))
    VAL_ATTR = DIFF_ABS
    -> ExpressionEvaluator_11
ExpressionEvaluator_11
    ACTION = Create New Attribute
    EXPRESSION = (@Value(DIFF_ABS)/(@Value(ANZAHL_ALT)/100.0))
    VAL_ATTR = DIFF_REL
    -> Sorter_6
Sorter_6
    SORT_PARM = DIFF_ABS NUMERIC ASCENDING
    SORTED -> Statistik_EOP (writer XLSXW_1)
Statistik_EOP (writer XLSXW_1)
    attributes: BFSNR number(6), ANZAHL_ALT number(12), ANZAHL_NEU number(12), DIFF_ABS number(9), DIFF_REL number(9)
verschwundeGDE_EOP (writer XLSXW_1)
    attributes: BFSNR number(6), ANZAHL number(12)
hinzugekommeGDE_EOP (writer XLSXW_1)
    attributes: BFSNR number(6), ANZAHL number(12)

Bookmark: Kontrolle ob BFSNR korrekt (Vergleich mit A_GEMEINDE_INFOS)
Note: Prüft, ob die BFSNR in NONAMF korrekt abgefüllt sind
SQLCreator_32
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_NONAMF t1
      where t1.bfsnr NOT IN (SELECT t2.bfsnr FROM A_GEMEINDE_INFOS t2 where t2.nbident=t1.nbident)
      GROUP BY t1.BFSNR
      ORDER BY t1.BFSNR asc
    RESULT -> NONAMF_BFSNR_nicht_korrekt (writer XLSXW_1)
NONAMF_BFSNR_nicht_korrekt (writer XLSXW_1)
    attributes: BFSNR number(6), ANZAHL number(12)
Note: Prüft, ob alle BFSNR in LIF korrekt abgefüllt sind
SQLCreator_31
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIF t1
      where t1.bfsnr NOT IN (SELECT t2.bfsnr FROM A_GEMEINDE_INFOS t2 where t2.nbident=t1.nbident)
      GROUP BY t1.BFSNR
      ORDER BY t1.BFSNR asc
    RESULT -> LIF_BFSNR_nicht_korrekt (writer XLSXW_1)
LIF_BFSNR_nicht_korrekt (writer XLSXW_1)
    attributes: BFSNR number(6), ANZAHL number(12)
Note: Prüft, ob die BFSNR in LITXT korrekt abgefüllt sind
SQLCreator_35
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LITXT t1
      where t1.bfsnr NOT IN (SELECT t2.bfsnr FROM A_GEMEINDE_INFOS t2 where t2.nbident=t1.nbident)
      GROUP BY t1.BFSNR
      ORDER BY t1.BFSNR asc
    RESULT -> LITXT_BFSNR_nicht_korrekt (writer XLSXW_1)
LITXT_BFSNR_nicht_korrekt (writer XLSXW_1)
    attributes: BFSNR number(6), ANZAHL number(12)
Note: Prüft, ob die BFSNR in LISRF korrekt abgefüllt sind
SQLCreator_36
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRF t1
      where t1.bfsnr NOT IN (SELECT t2.bfsnr FROM A_GEMEINDE_INFOS t2 where t2.nbident=t1.nbident)
      GROUP BY t1.BFSNR
      ORDER BY t1.BFSNR asc
    RESULT -> LISRF_BFSNR_nicht_korrekt (writer XLSXW_1)
LISRF_BFSNR_nicht_korrekt (writer XLSXW_1)
    attributes: BFSNR number(6), ANZAHL number(12)
Note: Prüft, ob die BFSNR in LISRTXT korrekt abgefüllt sind
SQLCreator_37
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRTXT t1
      where t1.bfsnr NOT IN (SELECT t2.bfsnr FROM A_GEMEINDE_INFOS t2 where t2.nbident=t1.nbident)
      GROUP BY t1.BFSNR
      ORDER BY t1.BFSNR asc
    RESULT -> LISRTXT_BFSNR_nicht_korrekt (writer XLSXW_1)
LISRTXT_BFSNR_nicht_korrekt (writer XLSXW_1)
    attributes: BFSNR number(6), ANZAHL number(12)
Note: Prüft, ob die BFSNR in LIPRJF korrekt abgefüllt sind
SQLCreator_38
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIPRJF t1
      where t1.bfsnr NOT IN (SELECT t2.bfsnr FROM A_GEMEINDE_INFOS t2 where t2.nbident=t1.nbident)
      GROUP BY t1.BFSNR
      ORDER BY t1.BFSNR asc
    RESULT -> LIPRJF_BFSNR_nicht_korrekt (writer XLSXW_1)
LIPRJF_BFSNR_nicht_korrekt (writer XLSXW_1)
    attributes: BFSNR number(6), ANZAHL number(12)
Note: Prüft, ob die BFSNR in LIPRJTXT korrekt abgefüllt sind
SQLCreator_39
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIPRJTXT t1
      where t1.bfsnr NOT IN (SELECT t2.bfsnr FROM A_GEMEINDE_INFOS t2 where t2.nbident=t1.nbident)
      GROUP BY t1.BFSNR
      ORDER BY t1.BFSNR asc
    RESULT -> LIPRJTXT_BFSNR_nicht_korrekt (writer XLSXW_1)
LIPRJTXT_BFSNR_nicht_korrekt (writer XLSXW_1)
    attributes: BFSNR number(6), ANZAHL number(12)
Note: Prüft, ob die BFSNR in LISRPRJF korrekt abgefüllt sind
SQLCreator_40
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRPRJF t1
      where t1.bfsnr NOT IN (SELECT t2.bfsnr FROM A_GEMEINDE_INFOS t2 where t2.nbident=t1.nbident)
      GROUP BY t1.BFSNR
      ORDER BY t1.BFSNR asc
    RESULT -> LISRPRJF_BFSNR_nicht_korrekt (writer XLSXW_1)
LISRPRJF_BFSNR_nicht_korrekt (writer XLSXW_1)
    attributes: BFSNR number(6), ANZAHL number(12)
Note: Prüft, ob die BFSNR in LISRPRJT korrekt abgefüllt sind
SQLCreator_41
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRPRJT t1
      where t1.bfsnr NOT IN (SELECT t2.bfsnr FROM A_GEMEINDE_INFOS t2 where t2.nbident=t1.nbident)
      GROUP BY t1.BFSNR
      ORDER BY t1.BFSNR asc
    RESULT -> LISRPRJT_BFSNR_nicht_korrekt (writer XLSXW_1)
LISRPRJT_BFSNR_nicht_korrekt (writer XLSXW_1)
    attributes: BFSNR number(6), ANZAHL number(12)

Bookmark: Kontrolle ob alle GBKR abgefüllt sind (Vergleich mit A_GEMEINDE_INFOS)
Note: Prüft, ob alle GBKR in LIF korrekt abgefüllt sind
SQLCreator_13 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIF t1
      where t1.gbkr NOT IN (SELECT t2.gbkr FROM A_GEMEINDE_INFOS t2 where t2.nbident=t1.nbident)
      GROUP BY t1.BFSNR
      ORDER BY t1.BFSNR asc
    RESULT -> LIF_GBKR_nicht_korrekt (writer XLSXW_1)
LIF_GBKR_nicht_korrekt (writer XLSXW_1) [off]
    attributes: BFSNR number(6), ANZAHL number(12)
Note: Prüft, ob alle GBKR in NONAMF korrekt abgefüllt sind
SQLCreator_14 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_NONAMF t1
      where t1.gbkr NOT IN (SELECT t2.gbkr FROM A_GEMEINDE_INFOS t2 where t2.nbident=t1.nbident)
      GROUP BY t1.BFSNR
      ORDER BY t1.BFSNR asc
    RESULT -> NONAMF_GBKR_nicht_korrekt (writer XLSXW_1)
NONAMF_GBKR_nicht_korrekt (writer XLSXW_1) [off]
    attributes: BFSNR number(6), ANZAHL number(12)
Note: Prüft, ob alle GBKR in LITXT korrekt abgefüllt sind
SQLCreator_15 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LITXT t1
      where t1.gbkr NOT IN (SELECT t2.gbkr FROM A_GEMEINDE_INFOS t2 where t2.nbident=t1.nbident)
      GROUP BY t1.BFSNR
      ORDER BY t1.BFSNR asc
    RESULT -> LITXT_GBKR_nicht_korrekt (writer XLSXW_1)
LITXT_GBKR_nicht_korrekt (writer XLSXW_1) [off]
    attributes: BFSNR number(6), ANZAHL number(12)
Note: Prüft, ob alle GBKR in LISRF korrekt abgefüllt sind
SQLCreator_16 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRF t1
      where t1.gbkr NOT IN (SELECT t2.gbkr FROM A_GEMEINDE_INFOS t2 where t2.nbident=t1.nbident)
      GROUP BY t1.BFSNR
      ORDER BY t1.BFSNR asc
    RESULT -> LISRF_GBKR_nicht_korrekt (writer XLSXW_1)
LISRF_GBKR_nicht_korrekt (writer XLSXW_1) [off]
    attributes: BFSNR number(6), ANZAHL number(12)
Note: Prüft, ob alle GBKR in LISRTXT korrekt abgefüllt sind
SQLCreator_17 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRTXT t1
      where t1.gbkr NOT IN (SELECT t2.gbkr FROM A_GEMEINDE_INFOS t2 where t2.nbident=t1.nbident)
      GROUP BY t1.BFSNR
      ORDER BY t1.BFSNR asc
    RESULT -> LISRTXT_GBKR_nicht_korrekt (writer XLSXW_1)
LISRTXT_GBKR_nicht_korrekt (writer XLSXW_1) [off]
    attributes: BFSNR number(6), ANZAHL number(12)
Note: Prüft, ob alle GBKR in LIPRJF korrekt abgefüllt sind
SQLCreator_18 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIPRJF t1
      where t1.gbkr NOT IN (SELECT t2.gbkr FROM A_GEMEINDE_INFOS t2 where t2.nbident=t1.nbident)
      GROUP BY t1.BFSNR
      ORDER BY t1.BFSNR asc
    RESULT -> LIPRJF_GBKR_nicht_korrekt (writer XLSXW_1)
LIPRJF_GBKR_nicht_korrekt (writer XLSXW_1) [off]
    attributes: BFSNR number(6), ANZAHL number(12)
Note: Prüft, ob alle GBKR in LIPRJTXT korrekt abgefüllt sind
SQLCreator_19 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LIPRJTXT t1
      where t1.gbkr NOT IN (SELECT t2.gbkr FROM A_GEMEINDE_INFOS t2 where t2.nbident=t1.nbident)
      GROUP BY t1.BFSNR
      ORDER BY t1.BFSNR asc
    RESULT -> LIPRJTXT_GBKR_nicht_korrekt (writer XLSXW_1)
LIPRJTXT_GBKR_nicht_korrekt (writer XLSXW_1) [off]
    attributes: BFSNR number(6), ANZAHL number(12)
Note: Prüft, ob alle GBKR in LISRPRJF korrekt abgefüllt sind
SQLCreator_20 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRPRJF t1
      where t1.gbkr NOT IN (SELECT t2.gbkr FROM A_GEMEINDE_INFOS t2 where t2.nbident=t1.nbident)
      GROUP BY t1.BFSNR
      ORDER BY t1.BFSNR asc
    RESULT -> LISRPRJF_GBKR_nicht_korrekt (writer XLSXW_1)
LISRPRJF_GBKR_nicht_korrekt (writer XLSXW_1) [off]
    attributes: BFSNR number(6), ANZAHL number(12)
Note: Prüft, ob alle GBKR in LISRPRJT korrekt abgefüllt sind
SQLCreator_21 [off]
    DATASET = $(NORM_DATABASE)
    EXPOSED_ATTRIBUTE_LIST = BFSNR,ANZAHL
    FORMAT = ORACLE_NONSPATIAL
    ORACLE_NONSPATIAL_PASSWORD = $(NORM_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(NORM_USERNAME)
    ORACLE_NONSPATIAL_USE_UNIFIED_DATE_ATTRS = YES
    SQL_STATEMENT:
      select t1.bfsnr, count(*) anzahl
      	from MOPUBE_LISRPRJT t1
      where t1.gbkr NOT IN (SELECT t2.gbkr FROM A_GEMEINDE_INFOS t2 where t2.nbident=t1.nbident)
      GROUP BY t1.BFSNR
      ORDER BY t1.BFSNR asc
    RESULT -> LISRPRJT_GBKR_nicht_korrekt (writer XLSXW_1)
LISRPRJT_GBKR_nicht_korrekt (writer XLSXW_1) [off]
    attributes: BFSNR number(6), ANZAHL number(12)
