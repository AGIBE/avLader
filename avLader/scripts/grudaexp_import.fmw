FME workspace grudaexp_import.fmw

Parameters:
- LOGFILE =
- CSVFOLDER =
- DATABASE =
- USERNAME =
- PASSWORD =   # PASSWORD PASSWORD

Readers:
- CSV2_2: CSV2 from $(CSVFOLDER)

Writers:
- ORACLE_NONSPATIAL_1: ORACLE_NONSPATIAL to $(DATABASE)

grundstueck_gebaeude (reader CSV2_2)
    attributes: GrundstueckREF string, GebaeudeREF string, Flaechenmass string, Gueltigkeit string, ErstellZeitpunkt string, GeschaeftNrBFS string, GeschaeftNrJahr string, GeschaeftNrNummer string, GeschaeftNrIndex string, MutNrNBIdent string, MutNrNummer string, col11 string
    -> AttributeValueMapper_9
AttributeValueMapper_9
    DIRECTION = Forward (Source To Destination)
    LUT = PROV,0,RECHTSG,1
    SRC = Gueltigkeit
    VAL_ATTR = Gueltigkeit_Aufgeloest
    -> AttributeManager_2
AttributeManager_2
    ATTR_TABLE:
      RENAME_SET_VALUE GrundstueckREF > GST_ID
      RENAME_SET_VALUE GebaeudeREF > GEB_ID
      RENAME_SET_VALUE Flaechenmass > AS_FLAECHE
      REMOVE Gueltigkeit
      RENAME_SET_VALUE ErstellZeitpunkt > ERSTELLZPK
      RENAME_SET_VALUE GeschaeftNrBFS > G_NR_BFS
      RENAME_SET_VALUE GeschaeftNrJahr > G_NR_JAHR
      RENAME_SET_VALUE GeschaeftNrNummer > G_NR_NR
      RENAME_SET_VALUE GeschaeftNrIndex > G_NR_INDEX
      RENAME_SET_VALUE MutNrNBIdent > M_NR_NBI
      RENAME_SET_VALUE MutNrNummer > M_NR_NR
      RENAME_SET_VALUE Gueltigkeit_Aufgeloest > GUELTIGKEI
      REMOVE col11
    -> Counter
Counter
    CNT_ATTR = OBJECTID
    DOMAIN = counter
    SCOPE = Local
    START = 1
    -> GRUDAEXP_GRUDAGZG (writer ORACLE_NONSPATIAL_1)
GRUDAEXP_GRUDAGZG (writer ORACLE_NONSPATIAL_1)
    attributes: OBJECTID number(38,0), GST_ID nvarchar(40), GEB_ID nvarchar(40), AS_FLAECHE number(38,0), GUELTIGKEI number(5,0), ERSTELLZPK nvarchar(20), G_NR_BFS number(5,0), G_NR_JAHR number(5,0), G_NR_NR number(5,0), G_NR_INDEX number(5,0), M_NR_NBI nvarchar(12), M_NR_NR nvarchar(12)
grundstueck (reader CSV2_2)
    attributes: GrundstueckId string, GemeindeBFSNr string, Gemeindename string, GemeindeNBIdent string, GBGemeindeKreisNr string, GBGemeindeNameDe string, GBGemeindeNameFr string, NBIdentKreis string, Amtssprache string, Nummer string, NummerZusatz string, EGRID string, GrundstueckArt string, Flaechenmass string, QualitaetsstandardAV string, FlaechenmaessigNichtAusgeschieden string, Gueltigkeit string, ErstellZeitpunkt string, GeschaeftNrBFS string, GeschaeftNrJahr string, GeschaeftNrNummer string, GeschaeftNrIndex string, MutNrNBIdent string, MutNrNummer string, col24 string
    -> AttributeValueMapper_5
AttributeValueMapper_5
    DIRECTION = Forward (Source To Destination)
    LUT = de,1,fr,2,it,3,rm,4,en,5
    SRC = Amtssprache
    VAL_ATTR = Amtssprache_aufgeloest
    -> AttributeValueMapper_6
AttributeValueMapper_6
    DIRECTION = Forward (Source To Destination)
    LUT = Liegenschaft,1,SelbstRecht.Baurecht,2,SelbstRecht.Quellenrecht,3,SelbstRecht.Konzessionsrecht,4,SelbstRecht.UebrigesRecht,5,SelbstRecht.weitere,6,Bergwerk,7
    SRC = GrundstueckArt
    VAL_ATTR = GruendstueckArt_aufgeloest
    -> AttributeValueMapper
AttributeValueMapper
    DIRECTION = Forward (Source To Destination)
    LUT = false,0,true,1
    SRC = FlaechenmaessigNichtAusgeschieden
    VAL_ATTR = FlaechnmaessigNichtAusgeschieden_Aufgeloest
    -> AttributeValueMapper_7
AttributeValueMapper_7
    DIRECTION = Forward (Source To Destination)
    LUT = AV93,1,PV74,2,PN.PN,3,PN.PN_def_anerkannt,4,PN.PN_prov_anerkannt,5,PEP,6,Unvermessen,7,Grafisch,8,Weitere,9
    SRC = QualitaetsstandardAV
    VAL_ATTR = Quaelitaetsstandard_aufgeloest
    -> AttributeValueMapper_8
AttributeValueMapper_8
    DIRECTION = Forward (Source To Destination)
    LUT = PROV,0,RECHTSG,1
    SRC = Gueltigkeit
    VAL_ATTR = Gueltigkeit_Aufgeloest
    -> AttributeManager
AttributeManager
    ATTR_TABLE:
      RENAME_SET_VALUE GrundstueckId > GST_ID
      RENAME_SET_VALUE GemeindeBFSNr > BFSNR
      RENAME_SET_VALUE Gemeindename > GEMNAME
      RENAME_SET_VALUE GemeindeNBIdent > NBIDENT
      RENAME_SET_VALUE GBGemeindeKreisNr > GBKRNR
      RENAME_SET_VALUE GBGemeindeNameDe > GBKRNAMEDE
      RENAME_SET_VALUE GBGemeindeNameFr > GBKRNAMEFR
      RENAME_SET_VALUE NBIdentKreis > NBIDENTKR
      REMOVE Amtssprache
      RENAME_SET_VALUE Nummer > GSTNR
      RENAME_SET_VALUE NummerZusatz > NR_ZUSATZ
      REMOVE GrundstueckArt
      RENAME_SET_VALUE Flaechenmass > FLAECHE
      REMOVE QualitaetsstandardAV
      REMOVE FlaechenmaessigNichtAusgeschieden
      REMOVE Gueltigkeit
      RENAME_SET_VALUE ErstellZeitpunkt > ERSTELLZPK
      RENAME_SET_VALUE GeschaeftNrBFS > G_NR_BFS
      RENAME_SET_VALUE GeschaeftNrJahr > G_NR_JAHR
      RENAME_SET_VALUE GeschaeftNrNummer > G_NR_NR
      RENAME_SET_VALUE GeschaeftNrIndex > G_NR_INDEX
      RENAME_SET_VALUE MutNrNBIdent > M_NR_NBI
      RENAME_SET_VALUE MutNrNummer > M_NR_NR
      REMOVE col24
      RENAME_SET_VALUE Amtssprache_aufgeloest > SPRACHE
      RENAME_SET_VALUE GruendstueckArt_aufgeloest > GSTART
      RENAME_SET_VALUE FlaechnmaessigNichtAusgeschieden_Aufgeloest > FLAE_AUSGE
      RENAME_SET_VALUE Quaelitaetsstandard_aufgeloest > Q_STAND_AV
      RENAME_SET_VALUE Gueltigkeit_Aufgeloest > GUELTIGKEI
    -> Counter_2
Counter_2
    CNT_ATTR = OBJECTID
    DOMAIN = counter
    SCOPE = Local
    START = 1
    -> GRUDAEXP_GRUDAGST (writer ORACLE_NONSPATIAL_1)
GRUDAEXP_GRUDAGST (writer ORACLE_NONSPATIAL_1)
    attributes: OBJECTID number(38,0), GST_ID nvarchar(40), BFSNR number(5,0), GEMNAME nvarchar(30), NBIDENT nvarchar(12), GBKRNR number(5,0), GBKRNAMEDE nvarchar(30), GBKRNAMEFR nvarchar(30), NBIDENTKR nvarchar(12), SPRACHE number(5,0), GSTNR nvarchar(12), NR_ZUSATZ nvarchar(12), EGRID nvarchar(14), GSTART number(5,0), FLAECHE number(10,0), Q_STAND_AV number(5,0), FLAE_AUSGE number(5,0), GUELTIGKEI number(5,0), ERSTELLZPK nvarchar(20), G_NR_BFS number(5,0), G_NR_JAHR number(5,0), G_NR_NR number(5,0), G_NR_INDEX number(5,0), M_NR_NBI nvarchar(12), M_NR_NR nvarchar(12)
gebaeude_eingang_adresse (reader CSV2_2)
    attributes: GebaeudeREF string, Strasse string, StrasseSprache2 string, GebauedeBezeichnung string, BenanntesGebiet string, BenanntesGebietSprache2 string, Hausnummer string, PLZ string, PLZZusatzziffern string, Ortschaft string, GWR_EGID string, GWR_EDID string, KantDID string, Gueltigkeit string, ErstellZeitpunkt string, col15 string
    -> AttributeValueMapper_11
AttributeValueMapper_11
    DIRECTION = Forward (Source To Destination)
    LUT = PROV,0,RECHTSG,1
    SRC = Gueltigkeit
    VAL_ATTR = Gueltigkeit_Aufgeloest
    -> AttributeManager_4
AttributeManager_4
    ATTR_TABLE:
      RENAME_SET_VALUE GebaeudeREF > GEB_ID
      RENAME_SET_VALUE Strasse > STRNAME
      RENAME_SET_VALUE StrasseSprache2 > STRNAME2
      RENAME_SET_VALUE GebauedeBezeichnung > GEB_BEZ
      RENAME_SET_VALUE BenanntesGebiet > BENGEBIET
      RENAME_SET_VALUE BenanntesGebietSprache2 > BENGEBIET2
      RENAME_SET_VALUE Hausnummer > GEBNR
      RENAME_SET_VALUE PLZZusatzziffern > PLZZ
      RENAME_SET_VALUE Ortschaft > ORTSCHAFT
      RENAME_SET_VALUE KantDID > BEDID
      REMOVE Gueltigkeit
      REMOVE col15
      RENAME_SET_VALUE Gueltigkeit_Aufgeloest > GUELTIGKEI
    -> Counter_3
Counter_3
    CNT_ATTR = OBJECTID
    DOMAIN = counter
    SCOPE = Local
    START = 1
    -> GRUDAEXP_GRUDAGAD (writer ORACLE_NONSPATIAL_1)
GRUDAEXP_GRUDAGAD (writer ORACLE_NONSPATIAL_1)
    attributes: OBJECTID number(38,0), GEB_ID nvarchar(40), STRNAME nvarchar(60), STRNAME2 nvarchar(60), GEB_BEZ nvarchar(60), BENGEBIET nvarchar(60), BENGEBIET2 nvarchar(60), GEBNR nvarchar(10), PLZ number(5,0), PLZZ number(5,0), ORTSCHAFT nvarchar(40), GWR_EGID nvarchar(12), GWR_EDID number(5,0), BEDID number(5,0), GUELTIGKEI number(5,0), ERSTELLZPK nvarchar(20)
gebaeude (reader CSV2_2)
    attributes: GebaeudeId string, GWR_EGID string, kantGID string, Nummer string, istProjektiert string, istUnterirdisch string, istEinzelobjekt string, GebaeudeArtDe string, GebaeudeArtFr string, GebaeudeArtIt string, GebaeudeArtCode string, GebauedeArtZusatz string, Flaechenmass string, Gueltigkeit string, ErstellZeitpunkt string, GeschaeftNrBFS string, GeschaeftNrJahr string, GeschaeftNrNummer string, GeschaeftNrIndex string, MutNrNBIdent string, MutNrNummer string, col21 string
    -> AttributeValueMapper_2
AttributeValueMapper_2
    DIRECTION = Forward (Source To Destination)
    LUT = false,0,true,1
    SRC = istEinzelobjekt
    VAL_ATTR = istEinzelobjekt_Aufgeloest
    -> AttributeValueMapper_3
AttributeValueMapper_3
    DIRECTION = Forward (Source To Destination)
    LUT = false,0,true,1
    SRC = istProjektiert
    VAL_ATTR = istProjektiert_Aufgeloest
    -> AttributeValueMapper_4
AttributeValueMapper_4
    DIRECTION = Forward (Source To Destination)
    LUT = false,0,true,1
    SRC = istUnterirdisch
    VAL_ATTR = istUnterirdisch_Aufgeloest
    -> AttributeValueMapper_10
AttributeValueMapper_10
    DIRECTION = Forward (Source To Destination)
    LUT = PROV,0,RECHTSG,1
    SRC = Gueltigkeit
    VAL_ATTR = Gueltigkeit_Aufgeloest
    -> AttributeManager_3
AttributeManager_3
    ATTR_TABLE:
      RENAME_SET_VALUE GebaeudeId > GEB_ID
      RENAME_SET_VALUE kantGID > KANT_GID
      RENAME_SET_VALUE Nummer > NUMMERZUS
      REMOVE istProjektiert
      REMOVE istUnterirdisch
      REMOVE istEinzelobjekt
      RENAME_SET_VALUE GebaeudeArtDe > GEB_ART_DE
      RENAME_SET_VALUE GebaeudeArtFr > GEB_ART_FR
      RENAME_SET_VALUE GebaeudeArtIt > GEB_ART_IT
      RENAME_SET_VALUE GebaeudeArtCode > GEBARTCODE
      RENAME_SET_VALUE GebauedeArtZusatz > GEBARTZUS
      RENAME_SET_VALUE Flaechenmass > GEBFLAECHE
      REMOVE Gueltigkeit
      RENAME_SET_VALUE ErstellZeitpunkt > ERSTELLZPK
      RENAME_SET_VALUE GeschaeftNrBFS > G_NR_BFS
      RENAME_SET_VALUE GeschaeftNrJahr > G_NR_JAHR
      RENAME_SET_VALUE GeschaeftNrNummer > G_NR_NR
      RENAME_SET_VALUE GeschaeftNrIndex > G_NR_INDEX
      RENAME_SET_VALUE MutNrNBIdent > M_NR_NBI
      RENAME_SET_VALUE MutNrNummer > M_NR_NR
      REMOVE col21
      RENAME_SET_VALUE istEinzelobjekt_Aufgeloest > EINZELOBJ
      RENAME_SET_VALUE istProjektiert_Aufgeloest > PROJEKT
      RENAME_SET_VALUE istUnterirdisch_Aufgeloest > UNTERIRD
      RENAME_SET_VALUE Gueltigkeit_Aufgeloest > GUELTIGKEI
    -> Counter_4
Counter_4
    CNT_ATTR = OBJECTID
    DOMAIN = counter
    SCOPE = Local
    START = 1
    -> GRUDAEXP_GRUDAGEB (writer ORACLE_NONSPATIAL_1)
GRUDAEXP_GRUDAGEB (writer ORACLE_NONSPATIAL_1)
    attributes: OBJECTID number(38,0), GEB_ID nvarchar(40), GWR_EGID number(38,0), KANT_GID number(38,0), NUMMERZUS nvarchar(12), PROJEKT number(5,0), UNTERIRD number(5,0), EINZELOBJ number(5,0), GEB_ART_DE nvarchar(30), GEB_ART_FR nvarchar(30), GEB_ART_IT nvarchar(30), GEBARTCODE nvarchar(4), GEBARTZUS nvarchar(255), GEBFLAECHE number(38,0), GUELTIGKEI number(5,0), ERSTELLZPK nvarchar(20), G_NR_BFS number(5,0), G_NR_JAHR number(5,0), G_NR_NR number(5,0), G_NR_INDEX number(5,0), M_NR_NBI nvarchar(12), M_NR_NR nvarchar(12)
bodenbedeckung_anteil (reader CSV2_2)
    attributes: GrundstueckREF string, Art string, Flaechenmass string, ArtBezeichnung string, LNAnteil string, Gueltigkeit string, ErstellZeitpunkt string, GeschaeftNrBFS string, GeschaeftNrJahr string, GeschaeftNrNummer string, GeschaeftNrIndex string, MutNrNBIdent string, MutNrNummer string, col13 string
    -> AttributeValueMapper_12
AttributeValueMapper_12
    DIRECTION = Forward (Source To Destination)
    LUT = PROV,0,RECHTSG,1
    SRC = Gueltigkeit
    VAL_ATTR = Gueltigkeit_Aufgeloest
    -> AttributeManager_5
AttributeManager_5
    ATTR_TABLE:
      RENAME_SET_VALUE GrundstueckREF > GST_ID
      RENAME_SET_VALUE Art > ART
      RENAME_SET_VALUE Flaechenmass > FLAECHENT
      RENAME_SET_VALUE ArtBezeichnung > ART_BEZ
      RENAME_SET_VALUE LNAnteil > LN_ANTEIL
      REMOVE Gueltigkeit
      RENAME_SET_VALUE ErstellZeitpunkt > ERSTELLZPK
      RENAME_SET_VALUE GeschaeftNrBFS > G_NR_BFS
      RENAME_SET_VALUE GeschaeftNrJahr > G_NR_JAHR
      RENAME_SET_VALUE GeschaeftNrNummer > G_NR_NR
      RENAME_SET_VALUE GeschaeftNrIndex > G_NR_INDEX
      RENAME_SET_VALUE MutNrNBIdent > M_NR_NBI
      RENAME_SET_VALUE MutNrNummer > M_NR_NR
      REMOVE col13
      RENAME_SET_VALUE Gueltigkeit_Aufgeloest > GUELTIGKEI
    -> Counter_5
Counter_5
    CNT_ATTR = OBJECTID
    DOMAIN = counter
    SCOPE = Local
    START = 1
    -> GRUDAEXP_GRUDABBF (writer ORACLE_NONSPATIAL_1)
GRUDAEXP_GRUDABBF (writer ORACLE_NONSPATIAL_1)
    attributes: OBJECTID number(38,0), GST_ID nvarchar(40), ART nvarchar(40), FLAECHENT number(38,0), ART_BEZ nvarchar(40), LN_ANTEIL number(38,0), GUELTIGKEI number(5,0), ERSTELLZPK nvarchar(20), G_NR_BFS number(5,0), G_NR_JAHR number(5,0), G_NR_NR number(5,0), G_NR_INDEX number(5,0), M_NR_NBI nvarchar(12), M_NR_NR nvarchar(12)
