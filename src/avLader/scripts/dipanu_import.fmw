FME workspace dipanu_import.fmw

Parameters:
- LOGFILE =
- NORM_CONNECTIONFILE =
- GPS1_CONNECTIONFILE =
- AV01_CONNECTIONFILE =

Readers:
- GEODATABASE_SDE_1: GEODATABASE_SDE
- GEODATABASE_SDE_2: GEODATABASE_SDE
- GEODATABASE_SDE_3: GEODATABASE_SDE
- GEODATABASE_SDE_4: GEODATABASE_SDE

Writers:
- GEODATABASE_SDE_5: GEODATABASE_SDE

Erstelle_DIPANUpointID
    BFSNR = @Value(BFSNR)
    GBKR = @Value(GBKR)
    GSTNR = @Value(GSTNR)
    GZNR = @Value(GZNR)
    StringConcatenator_4_OUTPUT_51 -> FeatureMerger_9 [REQUESTOR]
Erstelle_DIPANUpointID_2
    BFSNR = @Value(BFSNR)
    GBKR = @Value(GBKR)
    GSTNR = @Value(GSTNR)
    GZNR = @Value(GZNR)
    StringConcatenator_4_OUTPUT_51 -> PointOnAreaOverlayer [POINT]
    StringConcatenator_4_OUTPUT_51 -> FeatureMerger_12 [REQUESTOR]
Note: NORM.A_GEMEINDE_INFOS
A_GEMEINDE_INFOS (reader GEODATABASE_SDE_2)
    attributes: OBJECTID integer, BFSNR smallint, GBKR smallint, GEMNAME char(50), GBKRNAME char(50), GEMGBKRN char(80), GEMGBKRI integer, NBIDENT char(12), SPRACHE char(1), GANZEGEM smallint
    -> AttributeRemover_9
    -> AttributeCreator_17
AttributeRemover_9
    REMOVE_ATTRS = OBJECTID,SPRACHE,GANZEGEM
    -> BulkAttributeRenamer
    -> BulkAttributeRenamer_3
BulkAttributeRenamer_3
    ATTRCHOICE = All Attributes
    MODE_CHOICE = RENAME
    PATTERN_ACTION_DISP = ADDPREFIX
    REPLACE_STR = NB_
    -> FeatureMerger_7 [SUPPLIER]
Note: Fiktive Elemente werden aussortiert
Tester_2
    BOOL_OP = OR
    TEST_CLAUSE = CASE_INSENSITIVE_TEST @Value(NUMMER) CONTAINS fi
    FAILED -> FeatureMerger_3 [SUPPLIER]
    FAILED -> FeatureMerger [SUPPLIER]
PointOnAreaOverlayer
    ATTR_ACCUM_MODE = Merge Incoming
    ATTR_CONFLICT_RES = Use Original
    DEAGGREGATE_INPUT = Yes
    OV_ATTR = _overlaps
    POLYS_FIRST = NO
    POINT -> Tester_8
Tester_8
    BOOL_OP = OR
    TEST_CLAUSE = TEST @Value(_overlaps) > 0
    PASSED -> FeatureMerger_12 [SUPPLIER]
    PASSED -> FeatureMerger_9 [SUPPLIER]
FeatureMerger_9
    ATTR_ACCUM_MODE = Merge Supplier
    ATTR_CONFLICT_RES = Use Requestor
    IGNORE_NULLS = No
    JOIN_KEYS = @Value(_DIPANUpointID) @Value(_DIPANUpointID) AUTO
    MERGE_TYPE = Attributes Only
    PROCESS_DUPS = NO
    REJECT_NULL_MISSING_KEYS = No
    SUPPLIERS_FIRST = No
    UNMERGED_REQUESTOR -> AttributeManager_7
AttributeManager_7
    ATTR_TABLE = SET_TO PROJSTAT_ID = FME_CONDITIONAL:DEFAULT_VALUE'1'BOOL_OP;OR;COMPOSITE_TEST;<Unused>;TEST @Value(PROJSTAT) = 0;TEST @Value(PROJSTAT) = 2'0'FME_NUM_CONDITIONS2___
    -> StringConcatenator_10
StringConcatenator_10
    ACTION = Create New Attribute
    PARM_LINE = @Value(BFSNR)@Value(GBKR)@Value(PROJSTAT_ID)@Value(GSTNR)
    VAL_ATTR = _DIPANUpointIDav
    -> FeatureMerger_8 [REQUESTOR]
FeatureMerger_12
    ATTR_ACCUM_MODE = Merge Supplier
    ATTR_CONFLICT_RES = Use Requestor
    IGNORE_NULLS = No
    JOIN_KEYS = @Value(_DIPANUpointID) @Value(_DIPANUpointID) AUTO
    MERGE_TYPE = Attributes Only
    PROCESS_DUPS = NO
    REJECT_NULL_MISSING_KEYS = No
    SUPPLIERS_FIRST = No
    UNMERGED_REQUESTOR -> DuplicateRemover_3
Note: Fiktive Elemente werden aussortiert
Tester_3
    BOOL_OP = OR
    TEST_CLAUSE = CASE_INSENSITIVE_TEST @Value(NUMMER) CONTAINS fi
    FAILED -> FeatureMerger_4 [SUPPLIER]
    FAILED -> FeatureMerger_2 [SUPPLIER]
MultipleGeometryFilter
    NOT_CONTAINS -> Deaggregator
    <REJECTED> -> AttributeTrimmer
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_3
AreaCalculator_3
    AREA_ATTR = _area_TEMP
    AREA_TYPE = Plane Area
    MULT = 1
    -> MinimumAreaForcer
MinimumAreaForcer
    MINAREA = 0.3
    UNTOUCHED -> Aggregator_3
Aggregator_3
    ACCUM_ATTRS_NAME = Drop Incoming Attributes
    AGGREGATE_TYPE = Homogeneous Collection (If Possible)
    GROUP_BY = PROJLIEGENSCHAFT_VON _xmin SHAPE.LEN nb_LISTE_GEMGBKRN SELBSTRECHT_VON GBKRNAME LIEGENSCHAFT_VON BFSNR MITGEOM _ymin YMAX ENTSTEHUNG GZNR OBJID XMAX XMIN nb_LISTE_GEMGBKRI GUELTIGKEIT NBIDENT geodb_oid nb_LISTE_GBKRNAME QF QUALITAET OBJECTID X PROJSTAT GEMKR_NAME SPRACHE GSTBEZ VOLLSTAENDIGKEIT_TXT EGRID UNVERBI _zmin ART_TXT VOLLSTAENDIGKEIT _xmax _DIPANUpointIDav QV GZSTAT QUALITAET_TXT SHAPE.AREA GBFLAE TEILFLAE YMIN nb_LISTE_GEMNAME UP5 nb_LISTE_NBIDENT GSTART GSTNR GSTTEIL Y GEMKR_ID GBKR _ymax _zmax GEMNAME GUELTIGKEIT_TXT TECHFLAE PROJSELBSTRECHT_VON
    MODE = Geometry - Assemble One Level
    ORDERED = No
    SEP = ,
    AGGREGATE -> AttributeTrimmer
AttributeTrimmer
    SRC_ATTRS = GSTTEIL,GSTNR,GBKR
    TRIM_TO_NONE = Yes
    TRIM_TYPE = Both
    -> AttributeValueMapper_3
AttributeValueMapper_3
    DIRECTION = Forward (Source To Destination)
    LUT = 0,1,1,2,2,4,3,5,4,6,5,9
    SRC = QUALITAET
    VAL_ATTR = AV_QV
    -> AttributeTrimmer_2
AttributeTrimmer_2
    SRC_ATTRS = GSTTEIL
    TRIM_CHARS = 0
    TRIM_TO_NONE = Yes
    TRIM_TYPE = Left
    -> StringSearcher
StringSearcher
    CASE = no
    MATCHED_RESULT_ATTR = _first_match
    REGEXP = ^[A-Za-z]
    STRING_TO_SEARCH = @Value(GSTNR)
    MATCHED -> AttributeCopier
    NOT_MATCHED -> AttributeCreator_2
AttributeCopier
    ATTR_TABLE = COPY GSTNR > GZNR
    -> AttributeRemover
AttributeRemover
    REMOVE_ATTRS = GSTNR
    -> TestFilter
TestFilter
    DEFAULT_VALUE = <UNFILTERED>
    TEST_LIST:
      BOOL_OP,OR,COMPOSITE_TEST,<Unused>,TEST_CLAUSE,"TEST ""@Value(GZNR)"" BEGINS_WITH ""GZA""
      TEST ""@Value(GZNR)"" BEGINS_WITH ""AAF""",GZA,BOOL_OP,OR,COMPOSITE_TEST,<Unused>,TEST_CLAUSE,"TEST ""@Value(GZNR)"" BEGINS_WITH ""GZN""
      TEST ""@Value(GZNR)"" BEGINS_WITH ""NAF""",GZN,BOOL_OP,OR,COMPOSITE_TEST,<Unused>,TEST_CLAUSE,"TEST ""@Value(GZNR)"" BEGINS_WITH ""BLUSA""
      TEST ""@Value(GZNR)"" BEGINS_WITH ""ARTB""",BLUA,BOOL_OP,OR,COMPOSITE_TEST,<Unused>,TEST_CLAUSE,"TEST ""@Value(GZNR)"" BEGINS_WITH ""BLUN""
      TEST ""@Value(GZNR)"" BEGINS_WITH ""NRTB""",BLUN
    GZA -> AttributeCreator_3
    GZN -> AttributeCreator_4
    BLUA -> AttributeCreator_5
    BLUN -> AttributeCreator_6
    <UNFILTERED> -> AttributeCreator_7
AttributeCreator_3
    ATTR_TABLE = SET_TO GZSTAT = 1
    -> FeatureMerger_5 [REQUESTOR]
AttributeCreator_4
    ATTR_TABLE = SET_TO GZSTAT = 2
    -> FeatureMerger_5 [REQUESTOR]
AttributeCreator_5
    ATTR_TABLE = SET_TO GZSTAT = 3
    -> FeatureMerger_5 [REQUESTOR]
AttributeCreator_6
    ATTR_TABLE = SET_TO GZSTAT = 4
    -> FeatureMerger_5 [REQUESTOR]
AttributeCreator_7
    ATTR_TABLE = SET_TO GZSTAT = 9
    -> FeatureMerger_5 [REQUESTOR]
AttributeCreator_2
    ATTR_TABLE = SET_TO GZSTAT = 0
    -> Tester_6
Tester_6
    BOOL_OP = OR
    TEST_CLAUSE = TEST @Value(GSTNR) NOT_= 91360
    PASSED -> FeatureMerger_5 [REQUESTOR]
AttributeCreator_17
    ATTR_TABLE = SET_TO BFS = @Value(BFSNR)
    -> AttributeValueMapper_2
AttributeValueMapper_2
    DIRECTION = Forward (Source To Destination)
    LUT = D,1,F,2
    SRC = SPRACHE
    VAL_ATTR = SPRACHE_NEU
    -> AttributeRemover_2
AttributeRemover_2
    REMOVE_ATTRS = OBJECTID,BFSNR,GBKR,GEMNAME,GBKRNAME,GEMGBKRN,GEMGBKRI,NBIDENT,SPRACHE,GANZEGEM
    -> FeatureMerger_5 [SUPPLIER]
FeatureMerger_5
    ATTR_ACCUM_MODE = Merge Supplier
    ATTR_CONFLICT_RES = Use Requestor
    IGNORE_NULLS = No
    JOIN_KEYS = @Value(BFSNR) @Value(BFS) AUTO
    MERGE_TYPE = Attributes Only
    PROCESS_DUPS = NO
    REJECT_NULL_MISSING_KEYS = No
    SUPPLIERS_FIRST = No
    MERGED -> TestFilter_2
TestFilter_2
    DEFAULT_VALUE = <UNFILTERED>
    TEST_LIST = BOOL_OP,OR,COMPOSITE_TEST,<Unused>,TEST_CLAUSE,"TEST ""@Value(GZNR)"" > ""0""",GZNR > 0,BOOL_OP,OR,COMPOSITE_TEST,<Unused>,TEST_CLAUSE,"TEST ""@Value(PROJSTAT)"" = ""1""",PROJSTAT = 1
    GZNR > 0 -> AttributeCopier_2
    PROJSTAT = 1 -> AttributeCopier_4
    <UNFILTERED> -> StringConcatenator_3
StringConcatenator_3
    ACTION = Create New Attribute
    PARM_LINE = @Value(BFSNR)@Value(GBKR)@Value(GSTNR)
    VAL_ATTR = _ID_AV
    -> FeatureMerger_6 [REQUESTOR]
Note: NORM.GRUDAEXP_GRUDAGST
GRUDAEXP_GRUDAGST (reader GEODATABASE_SDE_2)
    attributes: OBJECTID integer, GST_ID char(40), BFSNR smallint, GEMNAME char(30), NBIDENT char(12), GBKRNR smallint, GBKRNAMEDE char(30), GBKRNAMEFR char(30), NBIDENTKR char(12), SPRACHE smallint, GSTNR char(12), NR_ZUSATZ char(12), EGRID char(14), GSTART smallint, FLAECHE integer, Q_STAND_AV smallint, FLAE_AUSGE smallint, GUELTIGKEI smallint, ERSTELLZPK char(20), G_NR_BFS smallint, G_NR_JAHR smallint, G_NR_NR smallint, G_NR_INDEX smallint, M_NR_NBI char(12), M_NR_NR char(12)
    -> Tester_15
Tester_15
    BOOL_OP = OR
    TEST_CLAUSE = TEST GBKRNR ATTRIBUTE_VALUE_NULL ""
    PASSED -> AttributeManager
    FAILED -> StringConcatenator
AttributeManager
    ATTR_TABLE = SET_TO GBKRNR = 0
    -> StringConcatenator
StringConcatenator
    ACTION = Create New Attribute
    PARM_LINE = @Value(BFSNR)@Value(GBKRNR)@Value(GSTNR)
    VAL_ATTR = _DIPANUpointIDgruda
    -> BulkAttributeRenamer_2
BulkAttributeRenamer_2
    ATTRCHOICE = All Attributes
    MODE_CHOICE = RENAME
    PATTERN_ACTION_DISP = ADDPREFIX
    REPLACE_STR = GRUDA_
    -> AttributeRemover_3
AttributeRemover_3
    REMOVE_ATTRS = GRUDA_M_NR_NBI,GRUDA_G_NR_JAHR,GRUDA_M_NR_NR,GRUDA_G_NR_NR,GRUDA_NBIDENTKR,GRUDA_OBJECTID,GRUDA_G_NR_BFS,GRUDA_GST_ID,GRUDA_G_NR_INDEX
    -> AttributeTrimmer_3
AttributeTrimmer_3
    SRC_ATTRS = GRUDA_ERSTELLZPK
    TRIM_TO_NONE = Yes
    TRIM_TYPE = Both
    -> StringReplacer
StringReplacer
    CASE = NO
    FIND_TEXT = ......$
    NO_MATCH = _FME_NO_OP_
    REGEXP = YES
    SRC_ATTRS = GRUDA_ERSTELLZPK
    -> AttributeTrimmer_4
AttributeTrimmer_4
    SRC_ATTRS = GRUDA_ERSTELLZPK
    TRIM_CHARS = " "
    TRIM_TO_NONE = Yes
    TRIM_TYPE = Both
    -> FeatureMerger_6 [SUPPLIER]
    -> FeatureMerger_8 [SUPPLIER]
    -> FeatureMerger_16 [SUPPLIER]
FeatureMerger_8
    ATTR_ACCUM_MODE = Merge Supplier
    ATTR_CONFLICT_RES = Use Requestor
    IGNORE_NULLS = Yes
    JOIN_KEYS = @Value(_DIPANUpointID) @Value(GRUDA__DIPANUpointIDgruda) AUTO
    MERGE_TYPE = Attributes Only
    PROCESS_DUPS = NO
    REJECT_NULL_MISSING_KEYS = No
    SUPPLIERS_FIRST = No
    MERGED -> AttributeCopier_5
AttributeCopier_5
    ATTR_TABLE = COPY GRUDA_FLAECHE > GBFLAE
    -> AttributeRemover_10
AttributeRemover_10
    REMOVE_ATTRS = _DIPANUpointID
    -> Tester_10
FeatureMerger_6
    ATTR_ACCUM_MODE = Merge Supplier
    ATTR_CONFLICT_RES = Use Requestor
    IGNORE_NULLS = No
    JOIN_KEYS = @Value(_ID_AV) @Value(GRUDA__DIPANUpointIDgruda) AUTO
    MERGE_TYPE = Attributes Only
    PROCESS_DUPS = NO
    REJECT_NULL_MISSING_KEYS = No
    SUPPLIERS_FIRST = No
    MERGED -> AttributeCopier_2
    UNMERGED_REQUESTOR -> AttributeCopier_4
AttributeCopier_4
    ATTR_TABLE = COPY TEILFLAE > GBFLAE
    -> AttributeCopier_2
AttributeCopier_2
    ATTR_TABLE:
      COPY GRUDA_FLAECHE > GBFLAE
      COPY _xmax > YMAX
      COPY _xmin > YMIN
      COPY _ymax > XMAX
      COPY _ymin > XMIN
      COPY GSTNR
      COPY SPRACHE_NEU > SPRACHE
    -> Tester
Tester
    BOOL_OP = OR
    TEST_CLAUSE = TEST GBFLAE ATTRIBUTE_VALUE_NULL ""
    PASSED -> FeatureMerger_7 [REQUESTOR]
    FAILED -> FeatureMerger_7 [REQUESTOR]
FeatureMerger_7
    ATTR_ACCUM_MODE = Merge Supplier
    ATTR_CONFLICT_RES = Use Requestor
    IGNORE_NULLS = No
    JOIN_KEYS = @Value(NBIDENT) @Value(NB_NBIDENT) AUTO
    MERGE_TYPE = Attributes Only
    PROCESS_DUPS = NO
    REJECT_NULL_MISSING_KEYS = No
    SUPPLIERS_FIRST = No
    MERGED -> AreaCalculator
AreaCalculator
    AREA_ATTR = _area
    AREA_TYPE = Plane Area
    MULT = 1
    -> AttributeCopier_3
AttributeCopier_3
    ATTR_TABLE:
      COPY NB_GEMGBKRN > GEMKR_NAME
      COPY NB_GEMNAME > GEMNAME
      COPY NB_GEMGBKRI > GEMKR_ID
      COPY NB_GBKRNAME > GBKRNAME
      COPY _area > TECHFLAE
    -> Tester_7
Tester_7
    BOOL_OP = OR
    TEST_CLAUSE = TEST @Value(GBKR) = 0
    PASSED -> AttributeCreator_13
    FAILED -> Sorter
AttributeCreator_13
    ATTR_TABLE = SET_TO GBKRNAME
    -> Sorter
Sorter
    SORT_PARM = X NUMERIC ASCENDING Y NUMERIC DESCENDING
    SORTED -> Tester_10
    SORTED -> AttributeCopier_6
Tester_10
    BOOL_OP = OR
    TEST_CLAUSE = TEST @Value(GBKR) = 0
    PASSED -> AttributeCreator_11
    FAILED -> AttributeRemover_4
AttributeCreator_11
    ATTR_TABLE = SET_TO GBKRNAME
    -> AttributeRemover_4
AttributeRemover_4
    REMOVE_ATTRS = YMIN,_zmin,VOLLSTAENDIGKEIT,OBJECTID,SELBSTRECHT_VON,_xmin,QUALITAET,_zmax,GEMKR_NAME,_ID_AV,Y,_ymin,geodb_oid,TEILFLAE,PROJSELBSTRECHT_VON,SHAPE.LEN,XMIN,_ymax,PROJLIEGENSCHAFT_VON,SHAPE.AREA,XMAX,_area,GUELTIGKEIT,YMAX,ENTSTEHUNG,_xmax,NB_NBIDENT,LIEGENSCHAFT_VON,UP5,GEMKR_ID,X
    -> Matcher
Matcher
    BLANK_AND_MISSING_DIFFER = No
    CNT_ATTR = _match_id
    LENIENT_MATCH = No
    MATCH = NONE
    MATCHATTRS = _DIPANUpointIDav
    MATCH_STRATEGY = Match Selected Attributes
    MATCHED -> ArcSDEGridSnapper
    NOT_MATCHED -> PythonCaller_4
ArcSDEGridSnapper
    OUTPUT_INT = No
    PRECISION_DISPLAY = High precision (53 bit)
    SCALE = 10000
    XMIN = 0
    YMIN = 0
    ZMIN = 0
    ZSCALE = 1
    SNAPPED -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> Tester_20
Tester_20
    BOOL_OP = AND
    TEST_CLAUSE:
      TEST @Value(GSTART) = 0
      TEST @Value(PROJSTAT) != 1
    PASSED -> AreaGapAndOverlapCleaner
    FAILED -> Dissolver_7
AreaGapAndOverlapCleaner
    CLEANING_TOLERANCE = 1
    CONNECT_Z_MODE = First Wins
    DEAGGREGATE_INPUT = YES
    FILL_ALL_GAPS = No
    MEASURE_TYPE = Continuous
    MISSING_VAL_MODE = Compute
    REPAIR_METHOD = Longest Boundary
    REPAIRED -> Dissolver_7
    REMNANTS -> Dissolver_7
Aggregator_4
    ACCUM_ATTRS_NAME = Use Attributes From One Feature
    AGGREGATE_TYPE = Homogeneous Collection (If Possible)
    GROUP_BY = _DIPANUpointIDav
    MODE = Geometry - Assemble One Level
    ORDERED = No
    SEP = ,
    AGGREGATE -> FeatureMerger_14 [REQUESTOR]
AttributeCopier_6
    ATTR_TABLE = COPY TECHFLAE > TEILFLAE
    -> AttributeRounder_2
AttributeRounder_2
    PLACES = 0
    ROUND_TYPE = Nearest
    SRC_ATTRS = TEILFLAE
    -> AttributeRemover_5
AttributeRemover_5
    REMOVE_ATTRS = GEMKR_NAME,UP5,GUELTIGKEIT,OBJECTID,SHAPE.LEN,_ID_AV,ENTSTEHUNG,GEMKR_ID,_zmin,_ymin,_xmin,_zmax,SHAPE.AREA,_ymax,PROJLIEGENSCHAFT_VON,NB_NBIDENT,QUALITAET,LIEGENSCHAFT_VON,SELBSTRECHT_VON,geodb_oid,_xmax,VOLLSTAENDIGKEIT,PROJSELBSTRECHT_VON,_area
    -> CenterPointReplacer
CenterPointReplacer
    MODE = Inside Point
    POINT -> CoordinateExtractor
CoordinateExtractor
    IND = 0
    MODE = Specify Coordinate
    X_ATTR = _yNeu
    Y_ATTR = _xNeu
    Z_ATTR = _zNeu
    Z_DEFAULT = -9999
    -> Tester_4
Tester_4
    BOOL_OP = OR
    TEST_CLAUSE = TEST @Value(GSTTEIL) > 0
    PASSED -> PythonCaller_2
    FAILED -> PythonCaller_5
PythonCaller_2
    PYTHONSOURCE:
      import fmeobjects
      # Template Function interface:
      def berechneGSTBEZ(feature):
          gstnr = str(feature.getAttribute("GSTNR"))
          gstart = int(feature.getAttribute("GSTART"))
          gzstat = int(feature.getAttribute("GZSTAT"))
          gznr = str(feature.getAttribute("GZNR"))
          sprache = int(feature.getAttribute("SPRACHE"))
          gstteil = str(feature.getAttribute("GSTTEIL"))

          gstbez = "-99"

          # Liegenschaften (LIE)
          if gstart == 0 and gzstat == 0:
              gstbez = gstnr + "." + gstteil
           # Liegenschaften (GZ)
          elif gstart == 0 and gzstat > 0:
              gstbez = gznr + "." + gstteil
          # Baurechte (LIE)
          elif gstart == 1 and gzstat == 0 and sprache == 1:
              gstbez = gstnr + "." + gstteil + " BR"
          elif gstart == 1 and gzstat == 0 and sprache == 2:
              gstbez = gstnr + "." + gstteil + " DS"
          # Quellrechte (LIE)
          elif gstart == 2 and gzstat == 0 and sprache == 1:
              gstbez = gstnr + "." + gstteil + " QR"
          elif gstart == 2 and gzstat == 0 and sprache == 2:
              gstbez = gstnr + "." + gstteil + " SO"
          # Kozessionsrechte (LIE)
          elif gstart == 3 and gzstat == 0 and sprache == 1:
              gstbez = gstnr + "." + gstteil + " KR"
          elif gstart == 3 and gzstat == 0 and sprache == 2:
              gstbez = gstnr + "." + gstteil + " CO"
          # übrige Rechte (LIE)
          elif gstart == 4 and gzstat == 0 and sprache == 1:
              gstbez = gstnr + "." + gstteil + " ÜR"
          elif gstart == 4 and gzstat == 0 and sprache == 2:
              gstbez = gstnr + "." + gstteil + " AD"
          # Baurechte (GZ)
          elif gstart == 1 and gzstat > 0 and sprache == 1:
              gstbez = gznr + "." + gstteil + " BR"
          elif gstart == 1 and gzstat > 0 and sprache == 2:
              gstbez = gznr + "." + gstteil + " DS"
          # Quellrechte (GZ)
          elif gstart == 2 and gzstat > 0 and sprache == 1:
              gstbez = gznr + "." + gstteil + " QR"
          elif gstart == 2 and gzstat > 0 and sprache == 2:
              gstbez = gznr + "." + gstteil + " SO"
          # Kozessionsrechte (GZ)
          elif gstart == 3 and gzstat > 0 and sprache == 1:
              gstbez = gznr + "." + gstteil + " KR"
          elif gstart == 3 and gzstat > 0 and sprache == 2:
              gstbez = gznr + "." + gstteil + " CO"
          # übrige Rechte (GZ)
          elif gstart == 4 and gzstat > 0 and sprache == 1:
              gstbez = gznr + "." + gstteil + " ÜR"
          elif gstart == 4 and gzstat > 0 and sprache == 2:
              gstbez = gznr + "." + gstteil + " AD"


          feature.setAttribute("GSTBEZ",gstbez)
    PYTHONSYMBOL = berechneGSTBEZ
    -> AttributeCreator_10
PythonCaller_5
    PYTHONSOURCE:
      import fmeobjects
      # Template Function interface:
      def berechneGSTBEZ(feature):
          gstnr = str(feature.getAttribute("GSTNR"))
          gstart = int(feature.getAttribute("GSTART"))
          gzstat = int(feature.getAttribute("GZSTAT"))
          gznr = str(feature.getAttribute("GZNR"))
          sprache = int(feature.getAttribute("SPRACHE"))

          gstbez = "-99"

          # Liegenschaften (LIE)
          if gstart == 0 and gzstat == 0:
              gstbez = gstnr
           # Liegenschaften (GZ)
          elif gstart == 0 and gzstat > 0:
              gstbez = gznr
          # Baurechte (LIE)
          elif gstart == 1 and gzstat == 0 and sprache == 1:
              gstbez = gstnr + " BR"
          elif gstart == 1 and gzstat == 0 and sprache == 2:
              gstbez = gstnr + " DS"
          # Quellrechte (LIE)
          elif gstart == 2 and gzstat == 0 and sprache == 1:
              gstbez = gstnr + " QR"
          elif gstart == 2 and gzstat == 0 and sprache == 2:
              gstbez = gstnr + " SO"
          # Kozessionsrechte (LIE)
          elif gstart == 3 and gzstat == 0 and sprache == 1:
              gstbez = gstnr + " KR"
          elif gstart == 3 and gzstat == 0 and sprache == 2:
              gstbez = gstnr + " CO"
          # übrige Rechte (LIE)
          elif gstart == 4 and gzstat == 0 and sprache == 1:
              gstbez = gstnr + " ÜR"
          elif gstart == 4 and gzstat == 0 and sprache == 2:
              gstbez = gstnr + " AD"
          # Baurechte (GZ)
          elif gstart == 1 and gzstat > 0 and sprache == 1:
              gstbez = gznr + " BR"
          elif gstart == 1 and gzstat > 0 and sprache == 2:
              gstbez = gznr + " DS"
          # Quellrechte (GZ)
          elif gstart == 2 and gzstat > 0 and sprache == 1:
              gstbez = gznr + " QR"
          elif gstart == 2 and gzstat > 0 and sprache == 2:
              gstbez = gznr + " SO"
          # Kozessionsrechte (GZ)
          elif gstart == 3 and gzstat > 0 and sprache == 1:
              gstbez = gznr + " KR"
          elif gstart == 3 and gzstat > 0 and sprache == 2:
              gstbez = gznr + " CO"
          # übrige Rechte (GZ)
          elif gstart == 4 and gzstat > 0 and sprache == 1:
              gstbez = gznr + " ÜR"
          elif gstart == 4 and gzstat > 0 and sprache == 2:
              gstbez = gznr + " AD"


          feature.setAttribute("GSTBEZ",gstbez)
    PYTHONSYMBOL = berechneGSTBEZ
    -> AttributeCreator_19
AttributeCreator_19
    ATTR_TABLE = SET_TO TEILFLAE = FME_NULL_VALUE
    -> AttributeCreator_10
AttributeCreator_10
    ATTR_TABLE:
      SET_TO Temp_GBFLAE = @Value(TECHFLAE)
      SET_TO X = @Value(_xNeu)
      SET_TO Y = @Value(_yNeu)
    -> AttributeRounder
AttributeRounder
    PLACES = 0
    ROUND_TYPE = Nearest
    SRC_ATTRS = Temp_GBFLAE
    -> StringConcatenator_14
StringConcatenator_14
    ACTION = Create New Attribute
    PARM_LINE = @Value(EGRID)@Value(PROJSTAT)@Value(Temp_GBFLAE)
    VAL_ATTR = _PUNKT_VERGLEICH_NEU
    -> DuplicateRemover_3
DuplicateRemover_3: DuplicateFilter
    INPUT_ORDERED_CHOICE = No
    KEYATTR = GSTTEIL BFSNR GZNR GSTART GBKR PROJSTAT GZSTAT GSTNR
    UNIQUE -> AttributeCreator_18
AttributeCreator_18
    ATTR_TABLE = SET_TO UP5 = 3
    -> StringConcatenator_4
StringConcatenator_4
    ACTION = Create New Attribute
    PARM_LINE = @Value(BFSNR)@Value(GBKR)
    VAL_ATTR = GEMGBKRI
    -> Tester_9
Tester_9
    BOOL_OP = OR
    TEST_CLAUSE = TEST @Value(GBKR) = 0
    PASSED -> AttributeCreator_15
    FAILED -> Tester_5
AttributeCreator_15
    ATTR_TABLE = SET_TO GBKRNAME
    -> Tester_5
Tester_5
    BOOL_OP = OR
    TEST_CLAUSE = TEST @Value(GBKR) = 0
    PASSED -> StringConcatenator_5
    FAILED -> StringConcatenator_6
StringConcatenator_5
    ACTION = Create New Attribute
    PARM_LINE = @Value(GEMNAME)
    VAL_ATTR = GEMGBKRN
    -> Tester_14
StringConcatenator_6
    ACTION = Create New Attribute
    PARM_LINE = @Value(GEMNAME) (@Value(GBKRNAME))
    VAL_ATTR = GEMGBKRN
    -> Tester_14
Tester_14
    BOOL_OP = OR
    TEST_CLAUSE = TEST @Value(X) < 1300000
    PASSED -> AttributeCreator_16
    FAILED -> CoordinateExtractor_2
CoordinateExtractor_2
    IND = 0
    MODE = Specify Coordinate
    X_ATTR = Y
    Y_ATTR = X
    Z_ATTR = _z
    Z_DEFAULT = -9999
    -> AttributeCreator_16
AttributeCreator_16
    ATTR_TABLE = SET_TO GBFLAE = @Value(GRUDA_FLAECHE)
    -> VertexCreator_2
VertexCreator_2
    MODE_NAME = Replace with Point
    XVAL = @Value(Y)
    YVAL = @Value(X)
    -> AttributeExposer
AttributeExposer
    ATTR_LIST = geodb_type
    -> AttributeRemover_7
AttributeRemover_7
    REMOVE_ATTRS = _z,geodb_type,_yNeu,_first_match,_PUNKT_VERGLEICH_NEU,fme_rejection_code,_xNeu,_zNeu
    -> AttributeRounder_3
AttributeRounder_3
    PLACES = 0
    ROUND_TYPE = Nearest
    SRC_ATTRS = XMIN YMIN YMAX X XMAX Y
    -> AttributeRounder_4
AttributeRounder_4
    PLACES = 3
    ROUND_TYPE = Nearest
    SRC_ATTRS = TECHFLAE
    -> AttributeRenamer
AttributeRenamer
    ATTR_TABLE:
      RENAME_SET_DEFAULT X > N_KOORD
      RENAME_SET_DEFAULT XMAX > N_MAX
      RENAME_SET_DEFAULT XMIN > N_MIN
      RENAME_SET_DEFAULT Y > E_KOORD
      RENAME_SET_DEFAULT YMAX > E_MAX
      RENAME_SET_DEFAULT YMIN > E_MIN
      RENAME_SET_DEFAULT GRUDA_ERSTELLZPK > LETZTEAEND
      RENAME_SET_DEFAULT GEMGBKRI > GENGBKRI
      RENAME_SET_DEFAULT GEMGBKRN > GENGBKRN
      RENAME_SET_DEFAULT AV_QV > QV
    -> Tester_18
    -> AttributeExpressionRenamer
Tester_18
    BOOL_OP = OR
    TEST_CLAUSE = TEST QV ATTRIBUTE_HAS_A_VALUE ""
    PASSED -> Tester_19
    FAILED -> SpatialFilter [Candidate]
AMO_ACTSTAT (reader GEODATABASE_SDE_2)
    attributes: OBJECTID integer, BFSNR smallint, GEMNAME char(60), LOS_NR smallint, LOS_B char(1), QUALITY smallint, FP smallint, BB smallint, EO smallint, HO smallint, NK smallint, LS smallint, RL smallint, AE smallint, HG smallint, BV smallint, GA smallint, DM char(5), AMOID char(6), REFRAME char(5), ANERKANNT date, SHAPE.AREA double, SHAPE.LEN double
    -> AttributeRemover_12
AttributeRemover_12
    REMOVE_ATTRS = FP,SHAPE.LEN,BFSNR,BB,ANERKANNT,EO,NK,AMOID,DM,SHAPE.AREA,GEMNAME,BV,HG,REFRAME,LOS_NR,OBJECTID,HO,RL,AE,LS,LOS_B,GA
    -> AttributeValueMapper
AttributeValueMapper
    DIRECTION = Forward (Source To Destination)
    LUT = 0,1,1,5,2,4,3,4,4,4,5,1,6,8,7,8,8,8,9,8,10,9,11,7
    SRC = QUALITY
    VAL_ATTR = SET_QV
    -> Dissolver_6
Dissolver_6
    ACCUM_INPUT_ATTRS = Use Attributes From One Feature
    CLEANING_TOLERANCE = None
    CONNECT_Z_MODE = First Wins
    DEAGGREGATE_INPUT = Yes
    GROUP_BY = QUALITY
    NO_OVRLP = No
    AREA -> SpatialFilter [Filter]
    AREA -> SpatialFilter_2 [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> GeometryValidator_2
GeometryValidator_2
    ISSUE_ATTR_NAME = _issues
    PRESETS = OGC
    REPAIR = Yes
    RULES = OGC_SIMPLE_CHECK  OGC_VALID_CHECK OGC_VERSION]V1.2.0]FME_CONTROLLER_QUERY_FILE]transformers\dependencies\geometryvalidator\OGC_VALID_CHECK.fme
    SUMMARY = Detailed
    PASSED -> AttributeManager_4
    REPAIRED -> AttributeManager_4
AttributeManager_4
    ATTR_TABLE = SET_TO QV = @Value(SET_QV)
    -> Tester_19
Tester_19
    BOOL_OP = AND
    TEST_CLAUSE:
      TEST @Value(QV) IN 7, 8
      TEST @Value(PROJSTAT) != 1
    PASSED -> AttributeManager_6
    FAILED -> Sorter_2
AttributeManager_6
    ATTR_TABLE = SET_TO PROJSTAT = 2
    -> Sorter_2
Sorter_2
    SORT_PARM = N_KOORD NUMERIC ASCENDING E_KOORD NUMERIC DESCENDING
    SORTED -> AttributeExpressionRenamer [off]
    SORTED -> DIPANU_DIPANUP (writer GEODATABASE_SDE_5)
DIPANU_DIPANUP (writer GEODATABASE_SDE_5)
    attributes: NBIDENT char(12), BFSNR smallint, GEMNAME char(60), GBKR smallint, GBKRNAME char(60), EGRID char(14), GSTNR integer, GSTTEIL char(2), GSTART smallint, GSTBEZ char(12), N_KOORD integer, E_KOORD integer, N_MAX integer, N_MIN integer, E_MAX integer, E_MIN integer, TEILFLAE integer, GBFLAE integer, TECHFLAE double, QV smallint, UP5 smallint, GZSTAT smallint, GZNR char(20), PROJSTAT smallint, MITGEOM smallint, SPRACHE smallint, UNVERBI smallint, LETZTEAEND char(10), GENGBKRI integer, GENGBKRN char(50)
AttributeExpressionRenamer: BulkAttributeRenamer
    ATTRCHOICE = All Attributes
    MODE_CHOICE = RENAME
    PATTERN_ACTION_DISP = ADDPREFIX
    REPLACE_STR = PUNKT_
    -> AttributeManager_8
AttributeManager_8
    ATTR_TABLE = SET_TO PROJSTAT_ID = FME_CONDITIONAL:DEFAULT_VALUE'1'BOOL_OP;OR;COMPOSITE_TEST;<Unused>;TEST @Value(PUNKT_PROJSTAT) = 0;TEST @Value(PUNKT_PROJSTAT) = 2'0'FME_NUM_CONDITIONS2___
    -> StringConcatenator_7
StringConcatenator_7
    ACTION = Create New Attribute
    PARM_LINE = @Value(PUNKT_BFSNR)@Value(PUNKT_GBKR)@Value(PROJSTAT_ID)@Value(PUNKT_GSTNR)
    VAL_ATTR = _DIPANUpointIDav2
    -> Tester_12
    -> Tester_13
    -> TestFilter_4
Tester_13
    BOOL_OP = OR
    TEST_CLAUSE = TEST @Value(PUNKT_UNVERBI) > 0
    PASSED -> FeatureMerger_14 [SUPPLIER]
FeatureMerger_14
    ATTR_ACCUM_MODE = Merge Supplier
    ATTR_CONFLICT_RES = Use Requestor
    IGNORE_NULLS = No
    JOIN_KEYS = @Value(_DIPANUpointIDav) @Value(_DIPANUpointIDav2) AUTO
    MERGE_TYPE = Attributes Only
    PROCESS_DUPS = NO
    REJECT_NULL_MISSING_KEYS = No
    SUPPLIERS_FIRST = No
    MERGED -> AttributeCreator_21
    UNMERGED_REQUESTOR -> AttributeCreator_20
AttributeCreator_21
    ATTR_TABLE = SET_TO UNVERBI = 1
    -> FeatureMerger_15 [REQUESTOR]
AttributeCreator_20
    ATTR_TABLE = SET_TO UNVERBI = 0
    -> FeatureMerger_15 [REQUESTOR]
Tester_12
    BOOL_OP = OR
    TEST_CLAUSE = TEST @Value(PUNKT_MITGEOM) > 0
    PASSED -> FeatureMerger_15 [SUPPLIER]
FeatureMerger_15
    ATTR_ACCUM_MODE = Merge Supplier
    ATTR_CONFLICT_RES = Use Requestor
    IGNORE_NULLS = No
    JOIN_KEYS = @Value(_DIPANUpointIDav) @Value(PUNKT__DIPANUpointIDav) AUTO
    MERGE_TYPE = Attributes Only
    PROCESS_DUPS = NO
    REJECT_NULL_MISSING_KEYS = No
    SUPPLIERS_FIRST = No
    MERGED -> AttributeCreator_23
    UNMERGED_REQUESTOR -> AttributeCreator_24
AttributeCreator_23
    ATTR_TABLE = SET_TO MITGEOM = 1
    -> AttributeRemover_6
AttributeCreator_24
    ATTR_TABLE = SET_TO MITGEOM = 0
    -> AttributeRemover_6
AttributeRemover_6
    REMOVE_ATTRS = GRUDA_EGRID,GRUDA_ERSTELLZPK,PUNKT_OBJECTID,PUNKT_nb_LISTE_GBKRNAME,PUNKT_nb_LISTE_GEMNAME,GRUDA_GBKRNR,PUNKT_GRUDA_FLAECHE,PUNKT_nb_LISTE_NBIDENT,nb_LISTE_GEMNAME,PUNKT_UP5,PUNKT_QF,PUNKT_GRUDA_BFSNR,nb_LISTE_GBKRNAME,PUNKT__issues{0}.location_sample.x,PUNKT__issues{0}.location_sample.y,PUNKT_E_MAX,PUNKT_TEILFLAE,PUNKT_QUALITY,PUNKT_SET_QV,PUNKT_NB_GEMGBKRN,_match_id,GRUDA_FLAECHE,NB_GBKRNAME,PUNKT__predicate,nb_LISTE_GEMGBKRI,PUNKT_GRUDA_GBKRNAMEDE,PUNKT_GSTTEIL,PUNKT_NB_BFSNR,GRUDA_GUELTIGKEI,PUNKT__issues{0}.issue_found,nb_LISTE_NBIDENT,PUNKT_E_KOORD,PUNKT_E_MIN,PUNKT__issues{0}.location_sample.z,PUNKT_nb_LISTE_GEMGBKRN,PUNKT_GRUDA_GSTNR,PUNKT_GRUDA_NBIDENT,NB_GBKR,GRUDA_NBIDENT,PUNKT_GRUDA_EGRID,GRUDA_BFSNR,PUNKT_nb_LISTE_GEMGBKRI,fme_rejection_code,nb_LISTE_GEMGBKRN,GRUDA_NR_ZUSATZ,PUNKT_N_MAX,PUNKT_NB_GEMGBKRI,PUNKT_Temp_GBFLAE,GRUDA_Q_STAND_AV,GRUDA_SPRACHE,PUNKT_GRUDA_GSTART,PUNKT_GRUDA_SPRACHE,GRUDA_GSTNR,_first_match,PUNKT_GRUDA_NR_ZUSATZ,GRUDA_GBKRNAMEFR,PUNKT_GRUDA_GBKRNAMEFR,PUNKT_GRUDA_GUELTIGKEI,GRUDA_FLAE_AUSGE,PUNKT_GRUDA_FLAE_AUSGE,NB_BFSNR,PUNKT_NB_GBKR,GRUDA_GBKRNAMEDE,GRUDA__DIPANUpointIDgruda,PUNKT_TECHFLAE,OBJID,PUNKT__issues{0}.count,NB_GEMNAME,GRUDA_GSTART,PUNKT_GRUDA_GBKRNR,PUNKT_NB_GEMNAME,PUNKT_N_KOORD,PUNKT_NB_GBKRNAME,PUNKT_GSTBEZ,GRUDA_GEMNAME,NB_GEMGBKRN,PUNKT_QUALITAET_TXT,PUNKT_OBJID,PUNKT_N_MIN,NB_GEMGBKRI,PUNKT_GRUDA_GEMNAME
    -> AttributeManager_2
AttributeManager_2
    ATTR_TABLE:
      SET_TO MITGEOM = @Value(PUNKT_MITGEOM)
      SET_TO GBKRNAME = @Value(PUNKT_GBKRNAME)
      SET_TO GBFLAE = @Value(PUNKT_GBFLAE)
      SET_TO NBIDENT = @Value(PUNKT_NBIDENT)
      SET_TO BFSNR = @Value(PUNKT_BFSNR)
      SET_TO GEMNAME = @Value(PUNKT_GEMNAME)
      SET_TO GBKR = @Value(PUNKT_GBKR)
      SET_TO EGRID = @Value(PUNKT_EGRID)
      SET_TO GSTNR = @Value(PUNKT_GSTNR)
      SET_TO GSTART = @Value(PUNKT_GSTART)
      SET_TO QV = @Value(PUNKT_QV)
      SET_TO GZSTAT = @Value(PUNKT_GZSTAT)
      SET_TO GZNR = @Value(PUNKT_GZNR)
      SET_TO PROJSTAT = @Value(PUNKT_PROJSTAT)
      SET_TO SPRACHE = @Value(PUNKT_SPRACHE)
      SET_TO GENGBKRI = @Value(PUNKT_GENGBKRI)
      SET_TO GENGBKRN = @Value(PUNKT_GENGBKRN)
    -> FeatureMerger_13 [REQUESTOR]
TestFilter_4
    DEFAULT_VALUE = <UNFILTERED>
    TEST_LIST = "BOOL_OP,OR,COMPOSITE_TEST,""""""<Unused>"""""",TEST_CLAUSE,TEST @Value(PUNKT_PROJSTAT) = 0",PROJSTAT_0,"BOOL_OP,OR,COMPOSITE_TEST,""""""<Unused>"""""",TEST_CLAUSE,TEST @Value(PUNKT_PROJSTAT) = 1",PROJSTAT_1,"BOOL_OP,OR,COMPOSITE_TEST,""""""<Unused>"""""",TEST_CLAUSE,TEST @Value(PUNKT_PROJSTAT) = 2",PROJSTAT_2
    PROJSTAT_2 -> FeatureMerger_13 [SUPPLIER]
FeatureMerger_13
    ATTR_ACCUM_MODE = Merge Supplier
    ATTR_CONFLICT_RES = Use Requestor
    IGNORE_NULLS = No
    JOIN_KEYS = @Value(_DIPANUpointIDav) @Value(PUNKT__DIPANUpointID) AUTO
    MERGE_TYPE = Attributes Only
    PROCESS_DUPS = NO
    REJECT_NULL_MISSING_KEYS = No
    SUPPLIERS_FIRST = No
    MERGED -> AttributeManager_9
    UNMERGED_REQUESTOR -> StringConcatenator_9
AttributeManager_9
    ATTR_TABLE = SET_TO PROJSTAT = @Value(PUNKT_PROJSTAT)
    -> StringConcatenator_9
StringConcatenator_9
    ACTION = Create New Attribute
    PARM_LINE = @Value(BFSNR)@Value(GBKR)@Value(GSTNR)
    VAL_ATTR = _DIPANUidGRUDA
    -> TestFilter_3
TestFilter_3
    DEFAULT_VALUE = <UNFILTERED>
    TEST_LIST = BOOL_OP,OR,COMPOSITE_TEST,<Unused>,TEST_CLAUSE,"TEST @Value(GZSTAT) = 0",@Value(GZSTAT) = 0,BOOL_OP,OR,COMPOSITE_TEST,<Unused>,TEST_CLAUSE,"TEST @Value(GZSTAT) > 0",@Value(GZSTAT) > 0,BOOL_OP,OR,COMPOSITE_TEST,<Unused>,TEST_CLAUSE,"TEST GZSTAT ATTRIBUTE_VALUE_NULL """"",GZSTAT ATTRIBUTE_VALUE_NULL
    @Value(GZSTAT) = 0 -> FeatureMerger_16 [REQUESTOR]
    @Value(GZSTAT) > 0 -> PythonCaller_4
FeatureMerger_16
    ATTR_ACCUM_MODE = Merge Supplier
    ATTR_CONFLICT_RES = Use Requestor
    IGNORE_NULLS = No
    JOIN_KEYS = @Value(_DIPANUidGRUDA) @Value(GRUDA__DIPANUpointIDgruda) AUTO
    MERGE_TYPE = Attributes Only
    PROCESS_DUPS = NO
    REJECT_NULL_MISSING_KEYS = No
    SUPPLIERS_FIRST = No
    MERGED -> PythonCaller_4
PythonCaller_4
    PYTHONSOURCE:
      import fmeobjects
      # Template Function interface:
      def berechneGSTBEZ(feature):
          gstnr = str(feature.getAttribute("GSTNR"))
          gstart = int(feature.getAttribute("GSTART"))
          gzstat = int(feature.getAttribute("GZSTAT"))
          gznr = str(feature.getAttribute("GZNR"))
          sprache = int(feature.getAttribute("SPRACHE"))

          gstbez = "-99"

          # Liegenschaften (LIE)
          if gstart == 0 and gzstat == 0:
              gstbez = gstnr
           # Liegenschaften (GZ)
          elif gstart == 0 and gzstat > 0:
              gstbez = gznr
          # Baurechte (LIE)
          elif gstart == 1 and gzstat == 0 and sprache == 1:
              gstbez = gstnr + " BR"
          elif gstart == 1 and gzstat == 0 and sprache == 2:
              gstbez = gstnr + " DS"
          # Quellrechte (LIE)
          elif gstart == 2 and gzstat == 0 and sprache == 1:
              gstbez = gstnr + " QR"
          elif gstart == 2 and gzstat == 0 and sprache == 2:
              gstbez = gstnr + " SO"
          # Kozessionsrechte (LIE)
          elif gstart == 3 and gzstat == 0 and sprache == 1:
              gstbez = gstnr + " KR"
          elif gstart == 3 and gzstat == 0 and sprache == 2:
              gstbez = gstnr + " CO"
          # übrige Rechte (LIE)
          elif gstart == 4 and gzstat == 0 and sprache == 1:
              gstbez = gstnr + " ÜR"
          elif gstart == 4 and gzstat == 0 and sprache == 2:
              gstbez = gstnr + " AD"
          # Baurechte (GZ)
          elif gstart == 1 and gzstat > 0 and sprache == 1:
              gstbez = gznr + " BR"
          elif gstart == 1 and gzstat > 0 and sprache == 2:
              gstbez = gznr + " DS"
          # Quellrechte (GZ)
          elif gstart == 2 and gzstat > 0 and sprache == 1:
              gstbez = gznr + " QR"
          elif gstart == 2 and gzstat > 0 and sprache == 2:
              gstbez = gznr + " SO"
          # Kozessionsrechte (GZ)
          elif gstart == 3 and gzstat > 0 and sprache == 1:
              gstbez = gznr + " KR"
          elif gstart == 3 and gzstat > 0 and sprache == 2:
              gstbez = gznr + " CO"
          # übrige Rechte (GZ)
          elif gstart == 4 and gzstat > 0 and sprache == 1:
              gstbez = gznr + " ÜR"
          elif gstart == 4 and gzstat > 0 and sprache == 2:
              gstbez = gznr + " AD"


          feature.setAttribute("GSTBEZ",gstbez)
    PYTHONSYMBOL = berechneGSTBEZ
    -> AreaCalculator_2
AreaCalculator_2
    AREA_ATTR = _TechFlae
    AREA_TYPE = Plane Area
    MULT = 1
    -> GeometryValidator
GeometryValidator
    ISSUE_ATTR_NAME = _issues
    PRESETS = Custom
    REPAIR = Yes
    RULES = NAN_REMOVAL  NULL_REMOVAL  TYPE_REPAIR ARC_ENDPOINT_TOLERANCE]0.001]ARC_ENDPOINT_TOLERANCE_MODE]Custom]CONNECT_Z_MODE]FIRST_WINS]FME_CONTROLLER_QUERY_FILE]transformers\dependencies\geometryvalidator\TYPE_REPAIR.fme SELF_INTERSECTING CHECK_HOLE_TOUCHING_POLYGON]Yes]CONNECT_Z_MODE_SI]AVERAGE]FME_CONTROLLER_QUERY_FILE]transformers\dependencies\geometryvalidator\SELF_INTERSECTING.fme PLANAR_SURFACE TOLERANCE]0.0]TOLERANCE_MODE]CUSTOM]CHECK_AREA]DO_NOT_CHECK_AREA]ANGULAR_TOLERANCE]0.0]ANGULAR_TOLERANCE_MODE]AUTO]FME_CONTROLLER_QUERY_FILE]transformers\dependencies\geometryvalidator\PLANAR_SURFACE.fme SHELL_VALIDATION  SOLID_VOID_REPAIR  OGC_SIMPLE_CHECK  OGC_VALID_CHECK  MISSING_TEXTURE_COORDINATES  MISSING_VERTEX_NORMALS
    SUMMARY = Detailed
    PASSED -> StringConcatenator_11
    FAILED -> StringConcatenator_11
    REPAIRED -> StringConcatenator_11
StringConcatenator_11
    ACTION = Create New Attribute
    PARM_LINE = @Value(BFSNR)@Value(GBKR)
    VAL_ATTR = GEMGBKRI
    -> Tester_11
Tester_11
    BOOL_OP = OR
    TEST_CLAUSE = TEST @Value(GBKR) = 0
    PASSED -> StringConcatenator_8
    FAILED -> StringConcatenator_2
StringConcatenator_8
    ACTION = Create New Attribute
    PARM_LINE = @Value(GEMNAME)
    VAL_ATTR = GENGBKRN
    -> AttributeCreator_14
StringConcatenator_2
    ACTION = Create New Attribute
    PARM_LINE = @Value(GEMNAME) (@Value(GBKRNAME))
    VAL_ATTR = GENGBKRN
    -> AttributeCreator_14
AttributeCreator_14
    ATTR_TABLE:
      SET_TO GENGBKRI = @Value(GEMGBKRI)
      SET_TO TECHFLAE = @Value(_TechFlae)
    -> AttributeRenamer_6
AttributeRenamer_6
    ATTR_TABLE:
      RENAME_SET_DEFAULT GRUDA_ERSTELLZPK > LETZTEAEND
      RENAME_SET_DEFAULT AV_QV > QV
      RENAME_SET_DEFAULT GRUDA_FLAECHE > GBFLAE
    -> Tester_16
Tester_16
    BOOL_OP = OR
    TEST_CLAUSE = TEST QV ATTRIBUTE_HAS_A_VALUE ""
    PASSED -> Tester_17
    FAILED -> GeometryValidator_3
GeometryValidator_3
    ISSUE_ATTR_NAME = _issues
    PRESETS = All
    REPAIR = Yes
    RULES = AREA_ORIENTATION AREA_ORIENTATION]VALID]FME_CONTROLLER_QUERY_FILE]transformers\dependencies\geometryvalidator\AREA_ORIENTATION.fme CONSECUTIVE_IDENTICAL_VERTICES_2D CHECK_Z]YES]FME_CONTROLLER_QUERY_FILE]transformers\dependencies\geometryvalidator\CONSECUTIVE_IDENTICAL_VERTICES_2D.fme MISSING_TEXTURE_COORDINATES  MISSING_VERTEX_NORMALS  NAN_REMOVAL PROCESS_MEASURE]NO]FME_CONTROLLER_QUERY_FILE]transformers\dependencies\geometryvalidator\NAN_REMOVAL.fme NULL_REMOVAL  OGC_SIMPLE_CHECK  OGC_VALID_CHECK OGC_VERSION]V1.2.0]FME_CONTROLLER_QUERY_FILE]transformers\dependencies\geometryvalidator\OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SELF_INTERSECTING CHECK_HOLE_TOUCHING_POLYGON]No]CONNECT_Z_MODE_SI]FIRST_WINS]FME_CONTROLLER_QUERY_FILE]transformers\dependencies\geometryvalidator\SELF_INTERSECTING.fme SHELL_VALIDATION FLIP_APPEARANCE_MODE]FLIP_APPEARANCES]FME_CONTROLLER_QUERY_FILE]transformers\dependencies\geometryvalidator\SHELL_VALIDATION.fme SOLID_VOID_REPAIR  TYPE_REPAIR CONNECT_Z_MODE]FIRST_WINS]ARC_ENDPOINT_TOLERANCE_MODE]Auto]ARC_ENDPOINT_TOLERANCE]0.0]FME_CONTROLLER_QUERY_FILE]transformers\dependencies\geometryvalidator\TYPE_REPAIR.fme MISMATCHED_DIMENSIONS FORCE_DIMENSION]2D]FME_CONTROLLER_QUERY_FILE]transformers\dependencies\geometryvalidator\MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers\dependencies\geometryvalidator\MISSING_MEASURES_AND_ELEVATIONS.fme
    SUMMARY = Detailed
    PASSED -> SpatialFilter_2 [Candidate]
    REPAIRED -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_5
AttributeManager_5
    ATTR_TABLE:
      SET_TO QV = @Value(SET_QV)
      REMOVE _issues{}.count
      REMOVE _issues{}.issue_found
      REMOVE _issues{}.location_sample.x
      REMOVE _issues{}.location_sample.y
      REMOVE _issues{}.location_sample.z
      REMOVE _issues{}.repair_state
    -> Tester_17
Tester_17
    BOOL_OP = AND
    TEST_CLAUSE:
      TEST @Value(QV) IN 7, 8
      TEST @Value(PROJSTAT) != 1
    PASSED -> AttributeManager_3
    FAILED -> Sorter_3
AttributeManager_3
    ATTR_TABLE = SET_TO PROJSTAT = 2
    -> Sorter_3
Sorter_3
    SORT_PARM = BFSNR NUMERIC ASCENDING GBKR NUMERIC ASCENDING
    SORTED -> DIPANU_DIPANUF (writer GEODATABASE_SDE_5)
DIPANU_DIPANUF (writer GEODATABASE_SDE_5)
    attributes: NBIDENT char(12), BFSNR smallint, GEMNAME char(60), GBKR smallint, GBKRNAME char(60), EGRID char(14), GSTNR integer, GSTART smallint, GSTBEZ char(12), GBFLAE integer, TECHFLAE double, QV smallint, GZSTAT smallint, GZNR char(20), PROJSTAT smallint, MITGEOM smallint, SPRACHE smallint, UNVERBI smallint, LETZTEAEND char(10), GENGBKRI integer, GENGBKRN char(50)

Bookmark: Grundstuecke aus dem FDS
Note: AV01.LI_Grundstueck
LI_Grundstueck (reader GEODATABASE_SDE_3)
    attributes: OBJECTID integer, OBJID char(32), ENTSTEHUNG char(32), NBIDENT char(12), NUMMER char(12), EGRIS_EGRID char(14), GUELTIGKEIT integer, GUELTIGKEIT_TXT char(14), VOLLSTAENDIGKEIT integer, VOLLSTAENDIGKEIT_TXT char(14), ART integer, ART_TXT char(28), GESAMTEFLAECHENMASS double
    -> FeatureMerger_17 [REQUESTOR]
Note: AV01.LI_Liegenschaft
LI_Liegenschaft (reader GEODATABASE_SDE_4)
    attributes: OBJECTID integer, OBJID char(32), LIEGENSCHAFT_VON char(32), NUMMERTEILGRUNDSTUECK char(12), FLAECHENMASS double, QUALITAET integer, QUALITAET_TXT char(20), SHAPE.AREA double, SHAPE.LEN double
    -> FeatureMerger [REQUESTOR]
Note: AV01.LI_SelbstRecht
LI_SelbstRecht (reader GEODATABASE_SDE_4)
    attributes: OBJECTID integer, OBJID char(32), SELBSTRECHT_VON char(32), NUMMERTEILGRUNDSTUECK char(12), FLAECHENMASS double, QUALITAET integer, QUALITAET_TXT char(20), SHAPE.AREA double, SHAPE.LEN double
    -> FeatureMerger_3 [REQUESTOR]

Bookmark: Projektierte Grundstuecke aus dem FDS
Note: AV01.LI_ProjLiegenschaft
LI_ProjLiegenschaft (reader GEODATABASE_SDE_4)
    attributes: OBJECTID integer, OBJID char(32), PROJLIEGENSCHAFT_VON char(32), NUMMERTEILGRUNDSTUECK char(12), FLAECHENMASS double, QUALITAET integer, QUALITAET_TXT char(20), SHAPE.AREA double, SHAPE.LEN double
    -> FeatureMerger_2 [REQUESTOR]
Note: AV01.LI_ProjGrundstueck
LI_ProjGrundstueck (reader GEODATABASE_SDE_3)
    attributes: OBJECTID integer, OBJID char(32), ENTSTEHUNG char(32), NBIDENT char(12), NUMMER char(12), EGRIS_EGRID char(14), GUELTIGKEIT integer, GUELTIGKEIT_TXT char(14), VOLLSTAENDIGKEIT integer, VOLLSTAENDIGKEIT_TXT char(14), ART integer, ART_TXT char(28), GESAMTEFLAECHENMASS double
    -> FeatureMerger_18 [REQUESTOR]
Note: AV01.LI_ProjSelbstRecht
LI_ProjSelbstRecht (reader GEODATABASE_SDE_4)
    attributes: OBJECTID integer, OBJID char(32), PROJSELBSTRECHT_VON char(32), NUMMERTEILGRUNDSTUECK char(12), FLAECHENMASS double, QUALITAET integer, QUALITAET_TXT char(20), SHAPE.AREA double, SHAPE.LEN double
    -> FeatureMerger_4 [REQUESTOR]

Bookmark: DIPANU ANALOG (Unvermessene Gebiete)
Note: GPS1.DIPANU_DIPANUF_ANALOG
DIPANU_DIPANUF_ANALOG (reader GEODATABASE_SDE_1)
    attributes: OBJECTID integer, NBIDENT char(12), BFSNR smallint, GEMNAME char(60), GBKR smallint, GBKRNAME char(60), EGRID char(14), GSTNR integer, GSTART smallint, GSTBEZ char(12), GBFLAE integer, TECHFLAE double, QF smallint, QV smallint, GZSTAT smallint, GZNR char(20), PROJSTAT smallint, MITGEOM smallint, SPRACHE smallint, UNVERBI smallint, GENGBKRI integer, GENGBKRN char(50), SHAPE.AREA double, SHAPE.LEN double
    -> Erstelle_DIPANUpointID [StringConcatenator_4_INPUT_51]
Note: GPS1.DIPANU_DIPANUP_ANALOG
DIPANU_DIPANUP_ANALOG (reader GEODATABASE_SDE_1)
    attributes: OBJECTID integer, NBIDENT char(12), BFSNR smallint, GEMNAME char(60), GBKR smallint, GBKRNAME char(60), EGRID char(14), GSTNR integer, GSTTEIL char(2), GSTART smallint, GSTBEZ char(12), X integer, Y integer, XMAX integer, XMIN integer, YMAX integer, YMIN integer, TEILFLAE integer, GBFLAE integer, TECHFLAE double, QF smallint, QV smallint, UP5 smallint, GZSTAT smallint, GZNR char(20), PROJSTAT smallint, MITGEOM smallint, SPRACHE smallint, UNVERBI smallint, GEMGBKRI integer,
      GEMGBKRN char(50)
    -> Erstelle_DIPANUpointID_2 [StringConcatenator_4_INPUT_51]

Bookmark: Grundstuecke erhalten Gemeinde- und Kreisname aus Gemeindeinfos Tabelle
BulkAttributeRenamer
    ATTRCHOICE = All Attributes
    MODE_CHOICE = RENAME
    PATTERN_ACTION_DISP = ADDPREFIX
    REPLACE_STR = nb_LISTE_
    -> FeatureMerger_17 [SUPPLIER]
    -> FeatureMerger_18 [SUPPLIER]
FeatureMerger_17
    ATTR_ACCUM_MODE = Merge Supplier
    ATTR_CONFLICT_RES = Use Requestor
    IGNORE_NULLS = Yes
    JOIN_KEYS = @Value(NBIDENT) @Value(nb_LISTE_NBIDENT) AUTO
    MERGE_TYPE = Attributes Only
    PROCESS_DUPS = NO
    REJECT_NULL_MISSING_KEYS = No
    SUPPLIERS_FIRST = No
    MERGED -> Tester_2
FeatureMerger_18
    ATTR_ACCUM_MODE = Merge Supplier
    ATTR_CONFLICT_RES = Use Requestor
    IGNORE_NULLS = Yes
    JOIN_KEYS = @Value(NBIDENT) @Value(nb_LISTE_NBIDENT) AUTO
    MERGE_TYPE = Attributes Only
    PROCESS_DUPS = NO
    REJECT_NULL_MISSING_KEYS = No
    SUPPLIERS_FIRST = No
    MERGED -> Tester_3

Bookmark: FDS joinen
FeatureMerger
    ATTR_ACCUM_MODE = Merge Supplier
    ATTR_CONFLICT_RES = Use Requestor
    IGNORE_NULLS = No
    JOIN_KEYS = @Value(LIEGENSCHAFT_VON) @Value(OBJID) AUTO
    MERGE_TYPE = Attributes Only
    PROCESS_DUPS = NO
    REJECT_NULL_MISSING_KEYS = No
    SUPPLIERS_FIRST = No
    MERGED -> AttributeRenamer_2
    MERGED -> PointOnAreaOverlayer [AREA]
AttributeRenamer_2
    ATTR_TABLE:
      RENAME_SET_DEFAULT EGRIS_EGRID > EGRID
      RENAME_SET_DEFAULT nb_LISTE_GBKR > GBKR
      RENAME_SET_DEFAULT ART > GSTART
      RENAME_SET_DEFAULT NUMMER > GSTNR
      RENAME_SET_DEFAULT NUMMERTEILGRUNDSTUECK > GSTTEIL
      RENAME_SET_DEFAULT GESAMTEFLAECHENMASS > GBFLAE
      RENAME_SET_DEFAULT FLAECHENMASS > TEILFLAE
      RENAME_SET_DEFAULT nb_LISTE_BFSNR > BFSNR
    -> Attributte_generieren [AttributeCreator_3_INPUT_98]
Attributte_generieren
    AttributeCreator_3_OUTPUT_98 -> Erdtelle_DIPANU_Point_ID_AV_4 [StringConcatenator_3_INPUT_226]
Erdtelle_DIPANU_Point_ID_AV_4
    BFSNR = @Value(BFSNR)
    GBKR = @Value(GBKR)
    GSTNR = @Value(GSTNR)
    PROJSTAT = @Value(PROJSTAT)
    StringConcatenator_3_OUTPUT_226 -> BoundsExtractor
FeatureMerger_3
    ATTR_ACCUM_MODE = Merge Supplier
    ATTR_CONFLICT_RES = Use Requestor
    IGNORE_NULLS = No
    JOIN_KEYS = @Value(SELBSTRECHT_VON) @Value(OBJID) AUTO
    MERGE_TYPE = Attributes Only
    PROCESS_DUPS = NO
    REJECT_NULL_MISSING_KEYS = No
    SUPPLIERS_FIRST = No
    MERGED -> AttributeRenamer_3
    MERGED -> PointOnAreaOverlayer [AREA]
AttributeRenamer_3
    ATTR_TABLE:
      RENAME_SET_DEFAULT nb_LISTE_GBKR > GBKR
      RENAME_SET_DEFAULT GESAMTEFLAECHENMASS > TECHFLAE
      RENAME_SET_DEFAULT NUMMER > GSTNR
      RENAME_SET_DEFAULT NUMMERTEILGRUNDSTUECK > GSTTEIL
      RENAME_SET_DEFAULT EGRIS_EGRID > EGRID
      RENAME_SET_DEFAULT ART > GSTART
      RENAME_SET_DEFAULT FLAECHENMASS > TEILFLAE
      RENAME_SET_DEFAULT nb_LISTE_BFSNR > BFSNR
    -> Attributte_generieren_2 [AttributeCreator_3_INPUT_98]
Attributte_generieren_2
    AttributeCreator_3_OUTPUT_98 -> Erdtelle_DIPANU_Point_ID_AV_3 [StringConcatenator_3_INPUT_226]
Erdtelle_DIPANU_Point_ID_AV_3
    BFSNR = @Value(BFSNR)
    GBKR = @Value(GBKR)
    GSTNR = @Value(GSTNR)
    PROJSTAT = @Value(PROJSTAT)
    StringConcatenator_3_OUTPUT_226 -> BoundsExtractor
Note: Liegenschaften und SDR werden aus Tabellen des FDS gejoint / -Der BoundsEctractor berechnet die Min/Max Koordinaten (BoundingBox) / Der AttributeCreator bereitet bereits
BoundsExtractor
    XMAX = _xmax
    XMIN = _xmin
    YMAX = _ymax
    YMIN = _ymin
    ZMAX = _zmax
    ZMIN = _zmin
    -> MultipleGeometryFilter
FeatureMerger_2
    ATTR_ACCUM_MODE = Merge Supplier
    ATTR_CONFLICT_RES = Use Requestor
    IGNORE_NULLS = No
    JOIN_KEYS = @Value(PROJLIEGENSCHAFT_VON) @Value(OBJID) AUTO
    MERGE_TYPE = Attributes Only
    PROCESS_DUPS = NO
    REJECT_NULL_MISSING_KEYS = No
    SUPPLIERS_FIRST = No
    MERGED -> Dissolver_2
    MERGED -> FeatureMerger_10 [SUPPLIER]
Dissolver_2
    ACCUM_INPUT_ATTRS = Drop Incoming Attributes
    CLEANING_TOLERANCE = None
    CONNECT_Z_MODE = First Wins
    DEAGGREGATE_INPUT = Yes
    GROUP_BY = NUMMERTEILGRUNDSTUECK QUALITAET NBIDENT NUMMER EGRIS_EGRID GUELTIGKEIT VOLLSTAENDIGKEIT ART nb_LISTE_BFSNR nb_LISTE_GBKR
    NO_OVRLP = No
    AREA -> FeatureMerger_10 [REQUESTOR]
FeatureMerger_10
    ATTR_ACCUM_MODE = Merge Supplier
    ATTR_CONFLICT_RES = Use Requestor
    IGNORE_NULLS = No
    JOIN_KEYS = @Value(EGRIS_EGRID) @Value(EGRIS_EGRID) AUTO
    MERGE_TYPE = Attributes Only
    PROCESS_DUPS = NO
    REJECT_NULL_MISSING_KEYS = No
    SUPPLIERS_FIRST = No
    MERGED -> AttributeRenamer_4
AttributeRenamer_4
    ATTR_TABLE:
      RENAME_SET_DEFAULT nb_LISTE_GBKR > GBKR
      RENAME_SET_DEFAULT GESAMTEFLAECHENMASS > TECHFLAE
      RENAME_SET_DEFAULT NUMMER > GSTNR
      RENAME_SET_DEFAULT NUMMERTEILGRUNDSTUECK > GSTTEIL
      RENAME_SET_DEFAULT EGRIS_EGRID > EGRID
      RENAME_SET_DEFAULT ART > GSTART
      RENAME_SET_DEFAULT FLAECHENMASS > TEILFLAE
      RENAME_SET_DEFAULT nb_LISTE_BFSNR > BFSNR
    -> Attributte_generieren_3 [AttributeCreator_3_INPUT_98]
Attributte_generieren_3
    AttributeCreator_3_OUTPUT_98 -> AttributeCreator
FeatureMerger_4
    ATTR_ACCUM_MODE = Merge Supplier
    ATTR_CONFLICT_RES = Use Requestor
    IGNORE_NULLS = No
    JOIN_KEYS = @Value(PROJSELBSTRECHT_VON) @Value(OBJID) AUTO
    MERGE_TYPE = Attributes Only
    PROCESS_DUPS = NO
    REJECT_NULL_MISSING_KEYS = No
    SUPPLIERS_FIRST = No
    MERGED -> Dissolver_3
    MERGED -> FeatureMerger_11 [SUPPLIER]
Dissolver_3
    ACCUM_INPUT_ATTRS = Drop Incoming Attributes
    CLEANING_TOLERANCE = None
    CONNECT_Z_MODE = First Wins
    DEAGGREGATE_INPUT = Yes
    GROUP_BY = NUMMERTEILGRUNDSTUECK FLAECHENMASS QUALITAET NBIDENT NUMMER EGRIS_EGRID GUELTIGKEIT VOLLSTAENDIGKEIT ART GESAMTEFLAECHENMASS nb_LISTE_BFSNR nb_LISTE_GBKR
    NO_OVRLP = No
    AREA -> FeatureMerger_11 [REQUESTOR]
FeatureMerger_11
    ATTR_ACCUM_MODE = Merge Supplier
    ATTR_CONFLICT_RES = Use Requestor
    IGNORE_NULLS = No
    JOIN_KEYS = @Value(EGRIS_EGRID) @Value(EGRIS_EGRID) AUTO
    MERGE_TYPE = Attributes Only
    PROCESS_DUPS = NO
    REJECT_NULL_MISSING_KEYS = No
    SUPPLIERS_FIRST = No
    MERGED -> AttributeRenamer_5
AttributeRenamer_5
    ATTR_TABLE:
      RENAME_SET_DEFAULT nb_LISTE_GBKR > GBKR
      RENAME_SET_DEFAULT GESAMTEFLAECHENMASS > TECHFLAE
      RENAME_SET_DEFAULT NUMMER > GSTNR
      RENAME_SET_DEFAULT NUMMERTEILGRUNDSTUECK > GSTTEIL
      RENAME_SET_DEFAULT EGRIS_EGRID > EGRID
      RENAME_SET_DEFAULT ART > GSTART
      RENAME_SET_DEFAULT FLAECHENMASS > TEILFLAE
      RENAME_SET_DEFAULT nb_LISTE_BFSNR > BFSNR
    -> Attributte_generieren_4 [AttributeCreator_3_INPUT_98]
Attributte_generieren_4
    AttributeCreator_3_OUTPUT_98 -> AttributeCreator
AttributeCreator
    ATTR_TABLE = SET_TO PROJSTAT = 1
    -> Erdtelle_DIPANU_Point_ID_AV_2 [StringConcatenator_3_INPUT_226]
Erdtelle_DIPANU_Point_ID_AV_2
    BFSNR = @Value(BFSNR)
    GBKR = @Value(GBKR)
    GSTNR = @Value(GSTNR)
    PROJSTAT = @Value(PROJSTAT)
    StringConcatenator_3_OUTPUT_226 -> BoundsExtractor_2
BoundsExtractor_2
    XMAX = _xmax
    XMIN = _xmin
    YMAX = _ymax
    YMIN = _ymin
    ZMAX = _zmax
    ZMIN = _zmin
    -> GeometryOGCValidator
GeometryOGCValidator: GeometryValidator
    ISSUE_ATTR_NAME = _issues
    PRESETS = Custom
    REPAIR = Yes
    RULES = "OGC_SIMPLE_CHECK "
    SUMMARY = Detailed
    PASSED -> MultipleGeometryFilter

Bookmark: New Bookmark
Dissolver_7
    ACCUM_INPUT_ATTRS = Use Attributes From One Feature
    CLEANING_TOLERANCE = None
    CONNECT_Z_MODE = First Wins
    DEAGGREGATE_INPUT = Yes
    GROUP_BY = _DIPANUpointIDav
    NO_OVRLP = No
    AREA -> Aggregator_4

FME custom transformer Erstelle_DIPANUpointID_AV_old

StringConcatenator_2_INPUT_87 (input)
    -> StringConcatenator_3
StringConcatenator_3
    ACTION = Create New Attribute
    PARM_LINE = @Value(BFSNR)@Value(GBKR)@Value(PROJSTAT)@Value(GSTNR)
    VAL_ATTR = _DIPANUpointIDav
    -> StringConcatenator_2_OUTPUT_87 (output)
StringConcatenator_2_OUTPUT_87 (output)

FME custom transformer Attributte_generieren

AttributeCreator_3_INPUT_98 (input)
    -> AttributeCreator_3
AttributeCreator_3
    ATTR_TABLE:
      SET_TO GEMNAME
      SET_TO PROJSTAT = 0
      SET_TO UNVERBI = 0
      SET_TO MITGEOM = 1
      SET_TO GBKRNAME
      SET_TO GSTBEZ
      SET_TO X
      SET_TO Y
      SET_TO XMAX
      SET_TO XMIN
      SET_TO YMAX
      SET_TO YMIN
      SET_TO TECHFLAE
      SET_TO QF
      SET_TO QV
      SET_TO UP5
      SET_TO GZSTAT = 0
      SET_TO GZNR
      SET_TO PROJSTAT = 0
      SET_TO MITGEOM = 1
      SET_TO SPRACHE
      SET_TO UNVERBI = 0
      SET_TO GEMKR_ID
      SET_TO GEMKR_NAME
    -> AttributeCreator_3_OUTPUT_98 (output)
AttributeCreator_3_OUTPUT_98 (output)

FME custom transformer Erdtelle_DIPANU_Point_ID_AV

Parameters:
- BFSNR = @Value(BFSNR)   # " " BFSNR
- GBKR = @Value(GBKR)   # " " GBKR
- PROJSTAT = @Value(PROJSTAT)   # " " PROJSTAT
- GSTNR = @Value(GSTNR)   # " " GSTNR

StringConcatenator_3_INPUT_226 (input)
    -> StringConcatenator_3
StringConcatenator_3
    ACTION = Create New Attribute
    PARM_LINE = $(BFSNR)$(GBKR)$(PROJSTAT)$(GSTNR)
    VAL_ATTR = _DIPANUpointIDav
    -> StringConcatenator_3_OUTPUT_226 (output)
StringConcatenator_3_OUTPUT_226 (output)

FME custom transformer AV_AttributeUmbenennen

AttributeRenamer_2_INPUT_100 (input)
    -> AttributeRenamer_2
AttributeRenamer_2
    ATTR_LIST = GB_KREIS,GBKR,"",GESAMTEFLAECHENMASS,TECHFLAE,"",NUMMER,GSTNR,"",NUMMERTEILGRUNDSTUECK,GSTTEIL,"",EGRIS_EGRID,EGRID,"",ART,GSTART,"",FLAECHENMASS,TEILFLAE,""
    -> AttributeRenamer_2_OUTPUT_100 (output)
AttributeRenamer_2_OUTPUT_100 (output)

FME custom transformer Erstelle_DIPANUpointID

Parameters:
- BFSNR = @Value(BFSNR)   # " " BFSNR
- GBKR = @Value(GBKR)   # " " GBKR
- GSTNR = @Value(GSTNR)   # " " GSTNR
- GZNR = @Value(GZNR)   # " " GZNR

StringConcatenator_4_INPUT_51 (input)
    -> StringConcatenator_4
StringConcatenator_4
    ACTION = Create New Attribute
    PARM_LINE = $(BFSNR)$(GBKR)$(GSTNR)$(GZNR)
    VAL_ATTR = _DIPANUpointID
    -> StringConcatenator_4_OUTPUT_51 (output)
StringConcatenator_4_OUTPUT_51 (output)
